-- COPYRIGHT NOTICE
-- Copyright (c) Radware Ltd. 2009
-- All rights reserved

ALTEON-CS-PHYSICAL-MIB DEFINITIONS ::= BEGIN

IMPORTS
    MODULE-IDENTITY, OBJECT-TYPE, Integer32, Counter32, Gauge32, TimeTicks,
    Unsigned32
        FROM SNMPv2-SMI
    DisplayString, PhysAddress
        FROM SNMPv2-TC
    BridgeId
        FROM BRIDGE-MIB
    aws-switch 
        FROM ALTEON-ROOT-MIB;

layer2 MODULE-IDENTITY
    LAST-UPDATED "200908050000Z" --  5 August, 2009
    ORGANIZATION "Radware Ltd."
    CONTACT-INFO "Lobby 1 (Visitors) and Lobby 2 (Deliveries)
                  575 Corporate Drive
                  Mahwah, NJ 07430
                  support@radware.com"
    DESCRIPTION
        "The MIB module for the Alteon OS Layer2 configuration, statistics and
         information ."
    REVISION "200908050000Z" --  5 August, 2009 
    DESCRIPTION
        "Added revision clause for SMIv2 compliance."
    ::= { aws-switch 2 }

layer2Configs     OBJECT IDENTIFIER ::= { layer2 1 }
layer2Stats       OBJECT IDENTIFIER ::= { layer2 2 }
layer2Info        OBJECT IDENTIFIER ::= { layer2 3 }
layer2Oper        OBJECT IDENTIFIER ::= { layer2 4 }

vlan              OBJECT IDENTIFIER ::= { layer2Configs 1 }
trunkgroup        OBJECT IDENTIFIER ::= { layer2Configs 2 }
stgCfg            OBJECT IDENTIFIER ::= { layer2Configs 3 }
mirroring         OBJECT IDENTIFIER ::= { layer2Configs 4 }
lacp              OBJECT IDENTIFIER ::= { layer2Configs 5 }
mstCfg            OBJECT IDENTIFIER ::= { layer2Configs 7 }

portTeamCfg       OBJECT IDENTIFIER ::= { layer2Configs 9 }
hwBypassConfig         OBJECT IDENTIFIER ::= { layer2Configs 11 }
mirrPortMirr      OBJECT IDENTIFIER ::= { mirroring 1 }

mstGeneralCfg     OBJECT IDENTIFIER ::= { mstCfg 1 }
mstCistCfg        OBJECT IDENTIFIER ::= { mstCfg 2 }

vadcVlan          OBJECT IDENTIFIER ::= { layer2Configs 10 }

lldp              OBJECT IDENTIFIER ::= { layer2Configs 12 }

mtuCfg		  OBJECT IDENTIFIER ::= { layer2Configs 13 }



fdbStats	  OBJECT IDENTIFIER ::= { layer2Stats 1 }
stpStats	  OBJECT IDENTIFIER ::= { layer2Stats 2 }

fdbInfo 	  OBJECT IDENTIFIER ::= { layer2Info 1 }
stpInfo           OBJECT IDENTIFIER ::= { layer2Info 2 }
lacpInfo          OBJECT IDENTIFIER ::= { layer2Info 3 }
cistInfo          OBJECT IDENTIFIER ::= { layer2Info 4 }
vlanInfo          OBJECT IDENTIFIER ::= { layer2Info 5 }

cistGeneralInfo   OBJECT IDENTIFIER ::= { cistInfo 1 }

portTeamInfo      OBJECT IDENTIFIER ::= { layer2Info 6  }

-- VLAN group
vlanMaxEnt OBJECT-TYPE
    SYNTAX  Integer32 
    MAX-ACCESS  read-only
    STATUS  current
    DESCRIPTION
        "The maximum number of rows in the VLAN configuration table,
         Note:This mib is supported only for VX instance of Virtualization."
    ::= { vlan 1 }

vlanMaxVlanID OBJECT-TYPE
    SYNTAX  Integer32 
    MAX-ACCESS  read-only
    STATUS  current
    DESCRIPTION
        "The maximum allowed VLAN ID,
         Note:This mib is supported only for VX instance of Virtualization."
    ::= { vlan 4 }

vlanCurCfgTable OBJECT-TYPE
    SYNTAX  SEQUENCE OF VlanCurCfgTableEntry
    MAX-ACCESS  not-accessible
    STATUS  current
    DESCRIPTION
        "The table of VLAN configuration,
         Note:This mib is supported only for VX instance of Virtualization."
    ::= { vlan 2 }

vlanCurCfgTableEntry OBJECT-TYPE
    SYNTAX  VlanCurCfgTableEntry
    MAX-ACCESS  not-accessible
    STATUS  current
    DESCRIPTION
        "A row in the VLAN configuration table."
    INDEX  { vlanCurCfgVlanId }
    ::= { vlanCurCfgTable 1 }

VlanCurCfgTableEntry ::= SEQUENCE {
    vlanCurCfgVlanId 		Integer32,
    vlanCurCfgPorts 		OCTET STRING,
    vlanCurCfgState 		INTEGER,
    vlanCurCfgBwmContract	Integer32,
    vlanCurCfgStg  	        Integer32,
    vlanCurCfgJumbo  	        INTEGER,
    vlanCurCfgLearn             INTEGER, 
    vlanCurCfgShared            INTEGER,
    vlanCurCfgIpv6LlaGen        INTEGER,
    vlanCurCfgRouterAdv         INTEGER,
    vlanCurCfgReTransInt        Unsigned32,
    vlanCurCfgMinIntBwAdv       INTEGER,
    vlanCurCfgMaxIntBwAdv       INTEGER,
    vlanCurCfgMtu               INTEGER,
    vlanCurCfgCurHopLimit       INTEGER,
    vlanCurCfgMFlag             INTEGER,
    vlanCurCfgOFlag             INTEGER,
    vlanCurCfgRTime             INTEGER,
    vlanCurCfgRlTime            INTEGER,
    vlanCurCfgPlTime            Unsigned32,
    vlanCurCfgVlTime            Unsigned32,
    vlanCurCfgOpInfo            INTEGER,
    vlanCurCfgApInfo            INTEGER,
    vlanCurCfgIpv6Lla           DisplayString,
    vlanCurCfgVlanName          DisplayString,
    vlanCurCfgMtuSize           Integer32,
    vlanCurCfgMtuFrag           INTEGER
    }

vlanCurCfgVlanId OBJECT-TYPE
    SYNTAX  Integer32
    MAX-ACCESS  read-only
    STATUS  current
    DESCRIPTION
        "The VLAN identifier,
         Note:This mib is supported only for VX instance of Virtualization."
    ::= { vlanCurCfgTableEntry 1 }

vlanCurCfgVlanName OBJECT-TYPE
    SYNTAX  DisplayString (SIZE(0..32))
    MAX-ACCESS  read-only
    STATUS  current
    DESCRIPTION
        "The VLAN name."
    ::= { vlanCurCfgTableEntry 2 }

vlanCurCfgPorts	OBJECT-TYPE
    SYNTAX  OCTET STRING
    MAX-ACCESS  read-only
    STATUS  current
    DESCRIPTION
        "The port list in the VLAN. The ports are presented in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
		   0 - The represented port does not belong to the VLAN"
    ::= { vlanCurCfgTableEntry 3 }

vlanCurCfgState	OBJECT-TYPE
    SYNTAX  INTEGER  {
	enabled(2),
	disabled(3),
        unsupported(2147483647)
	}
    MAX-ACCESS  read-only
    STATUS  current
    DESCRIPTION
        "Enable or disable a VLAN"
    ::= { vlanCurCfgTableEntry 4 }

vlanCurCfgBwmContract OBJECT-TYPE
    SYNTAX  Integer32  
    MAX-ACCESS  read-only
    STATUS  current
    DESCRIPTION
        "Default contract number the VLAN "
    ::= { vlanCurCfgTableEntry 5 }

vlanCurCfgStg OBJECT-TYPE
    SYNTAX  Integer32  
    MAX-ACCESS  read-only
    STATUS  current
    DESCRIPTION
        "The Spanning Tree Group for the VLAN."
    ::= { vlanCurCfgTableEntry 6 }

vlanCurCfgJumbo	OBJECT-TYPE
    SYNTAX  INTEGER  {
	enabled(2),
	disabled(3),
        unsupported(2147483647)
	}
    MAX-ACCESS  read-only
    STATUS  current
    DESCRIPTION
        "Enable or disable Jumbo frames on a VLAN"
    ::= { vlanCurCfgTableEntry 7 }

vlanCurCfgLearn OBJECT-TYPE
    SYNTAX  INTEGER  {
        enabled(2),
        disabled(3),
        unsupported(2147483647)
        }
    MAX-ACCESS  read-only
    STATUS  current
    DESCRIPTION
        "Enable or disable source MAC address learning on a VLAN"
    ::= { vlanCurCfgTableEntry 8 }

vlanCurCfgShared OBJECT-TYPE
    SYNTAX  INTEGER  {
        enabled(2),
        disabled(3),
        unsupported(2147483647)
        }
    MAX-ACCESS  read-only
    STATUS  current
    DESCRIPTION
        "Enable or disable shared property of a VLAN,
         This mib is supported only on VX platform."
    ::= { vlanCurCfgTableEntry 9 }

vlanCurCfgIpv6LlaGen OBJECT-TYPE
    SYNTAX INTEGER {
        enabled(2),
        disabled(3),
        unsupported(2147483647)
    }
    MAX-ACCESS read-only
    STATUS current
    DESCRIPTION
        "Enable/disable IPv6 Link Local Address Generation,
         This mib is supported only on VA and Stand Alone platforms."
    ::= { vlanCurCfgTableEntry 10 }

vlanCurCfgRouterAdv OBJECT-TYPE
    SYNTAX INTEGER {
        enabled(2),
        disabled(3),
        unsupported(2147483647)
    }
    MAX-ACCESS read-only
    STATUS current
    DESCRIPTION
        "Enable/disable router advertisement,
         This mib is supported only on VA and Stand Alone platforms."
    ::= { vlanCurCfgTableEntry 11 }

vlanCurCfgReTransInt OBJECT-TYPE
    SYNTAX Unsigned32 ( 0 .. 4294967295 )
    MAX-ACCESS read-only
    STATUS current
    DESCRIPTION
        "Retransmission interval,
         This mib is supported only on VA and Stand Alone platforms."
    ::= { vlanCurCfgTableEntry 12 }

vlanCurCfgMinIntBwAdv OBJECT-TYPE
    SYNTAX INTEGER ( 3 .. 1800 )
    MAX-ACCESS read-only
    STATUS current
    DESCRIPTION
        "Minimum interval between router advertisements,
         This mib is supported only on VA and Stand Alone platforms."
    ::= { vlanCurCfgTableEntry 13 }

vlanCurCfgMaxIntBwAdv OBJECT-TYPE
    SYNTAX INTEGER ( 4 .. 1800 )
    MAX-ACCESS read-only
    STATUS current
    DESCRIPTION
        "Maximum interval between router advertisements,
         This mib is supported only on VA and Stand Alone platforms."
    ::= { vlanCurCfgTableEntry 14 }

vlanCurCfgMtu OBJECT-TYPE
    SYNTAX INTEGER ( 1200 .. 1500 )
    MAX-ACCESS read-only
    STATUS current
    DESCRIPTION
        "Maximum Transmission Unit. Enter 0 for None,
         This mib is supported only on VA and Stand Alone platforms."
    ::= { vlanCurCfgTableEntry 15 }

vlanCurCfgCurHopLimit OBJECT-TYPE
    SYNTAX INTEGER ( 0 .. 255 )
    MAX-ACCESS read-only
    STATUS current
    DESCRIPTION
        "Current hop limit field,
         This mib is supported only on VA and Stand Alone platforms."
    ::= { vlanCurCfgTableEntry 16 }

vlanCurCfgMFlag OBJECT-TYPE
    SYNTAX INTEGER {
        enabled(2),
        disabled(3),
        unsupported(2147483647)
    }
    MAX-ACCESS read-only
    STATUS current
    DESCRIPTION
        "Enable / Disable Managed address configuration flag,
         This mib is supported only on VA and Stand Alone platforms."
    ::= { vlanCurCfgTableEntry 17 }

vlanCurCfgOFlag OBJECT-TYPE
    SYNTAX INTEGER {
        enabled(2),
        disabled(3),
        unsupported(2147483647)
    }
    MAX-ACCESS read-only
    STATUS current
    DESCRIPTION
        "Enable / Disable Other address configuration flag,
         This mib is supported only on VA and Stand Alone platforms."
    ::= { vlanCurCfgTableEntry 18 }

vlanCurCfgRTime OBJECT-TYPE
    SYNTAX INTEGER ( 0 .. 3600000 )
    MAX-ACCESS read-only
    STATUS current
    DESCRIPTION
        "Reachable time,
         This mib is supported only on VA and Stand Alone platforms."
    ::= { vlanCurCfgTableEntry 19 }

vlanCurCfgRlTime OBJECT-TYPE
    SYNTAX INTEGER ( 0 .. 9000 )
    MAX-ACCESS read-only
    STATUS current
    DESCRIPTION
        "Life Time.Enter 0 for None,
         This mib is supported only on VA and Stand Alone platforms."
    ::= { vlanCurCfgTableEntry 20 }

vlanCurCfgPlTime OBJECT-TYPE
    SYNTAX Unsigned32 ( 0 .. 4294967295 )
    MAX-ACCESS read-only
    STATUS current
    DESCRIPTION
        "Preferred life time,
         This mib is supported only on VA and Stand Alone platforms."
    ::= { vlanCurCfgTableEntry 21 }

vlanCurCfgVlTime OBJECT-TYPE
    SYNTAX Unsigned32 ( 0 .. 4294967295 )
    MAX-ACCESS read-only
    STATUS current
    DESCRIPTION
        "Valid life time,
         This mib is supported only on VA and Stand Alone platforms."
    ::= { vlanCurCfgTableEntry 22 }
    
vlanCurCfgOpInfo OBJECT-TYPE
    SYNTAX INTEGER {
        enabled(2),
        disabled(3),
        unsupported(2147483647)
    }
    MAX-ACCESS read-only
    STATUS current
    DESCRIPTION
        "Enable / Disable On-link flag in prefix,
         This mib is supported only on VA and Stand Alone platforms."
    ::= { vlanCurCfgTableEntry 23 }

vlanCurCfgApInfo OBJECT-TYPE
    SYNTAX INTEGER {
        enabled(2),
        disabled(3),
        unsupported(2147483647)
    }
    MAX-ACCESS read-only
    STATUS current
    DESCRIPTION
        "Enable / Disable Autonomous address configuration flag in prefix,
         This mib is supported only on VA and Stand Alone platforms."
    ::= { vlanCurCfgTableEntry 24 }

vlanCurCfgIpv6Lla OBJECT-TYPE
    SYNTAX DisplayString (SIZE(0..40))
    MAX-ACCESS  read-only
    STATUS  current
    DESCRIPTION
        "IPV6 Link Local Address,
         This mib is supported only on VA and Stand Alone platforms."
    ::= { vlanCurCfgTableEntry 25 }

vlanCurCfgMtuSize OBJECT-TYPE
     SYNTAX  Integer32 ( 1500..9216 )
     MAX-ACCESS  read-only
      STATUS  current
      DESCRIPTION
          "The VLAN MtuSize,
           Note:This mib is supported only for VX instance of Virtualization."
      ::= { vlanCurCfgTableEntry 26 }

vlanCurCfgMtuFrag OBJECT-TYPE
      SYNTAX  INTEGER  {
          enabled(2),
          disabled(3),
          unsupported(2147483647)
          }
      MAX-ACCESS  read-only
      STATUS  current
      DESCRIPTION
          "Enable or disable a VLAN MtuFrag"
      ::= { vlanCurCfgTableEntry 27 }

vlanNewCfgTable OBJECT-TYPE
    SYNTAX  SEQUENCE OF VlanNewCfgTableEntry
    MAX-ACCESS  not-accessible
    STATUS  current
    DESCRIPTION
        "The table of VLAN configuration,
         Note:This mib is supported only for VX instance of Virtualization."
    ::= { vlan 3 }

vlanNewCfgTableEntry OBJECT-TYPE
    SYNTAX  VlanNewCfgTableEntry
    MAX-ACCESS  not-accessible
    STATUS  current
    DESCRIPTION
        "A row in the VLAN configuration table."
    INDEX  { vlanNewCfgVlanId }
    ::= { vlanNewCfgTable 1 }

VlanNewCfgTableEntry ::= SEQUENCE {
    vlanNewCfgVlanId 		Integer32,
    vlanNewCfgVlanName 		DisplayString,
    vlanNewCfgPorts 		OCTET STRING,
    vlanNewCfgState 		INTEGER,
    vlanNewCfgAddPort 		Integer32,
    vlanNewCfgRemovePort	Integer32,
    vlanNewCfgBwmContract	Integer32,
    vlanNewCfgStg  	        Integer32,
    vlanNewCfgJumbo	        INTEGER,
    vlanNewCfgLearn             INTEGER,
    vlanNewCfgShared            INTEGER,
    vlanNewCfgIpv6LlaGen        INTEGER,
    vlanNewCfgRouterAdv         INTEGER,
    vlanNewCfgReTransInt        Unsigned32,
    vlanNewCfgMinIntBwAdv       INTEGER,
    vlanNewCfgMaxIntBwAdv       INTEGER,
    vlanNewCfgMtu               INTEGER,
    vlanNewCfgCurHopLimit       INTEGER,
    vlanNewCfgMFlag             INTEGER,
    vlanNewCfgOFlag             INTEGER,
    vlanNewCfgRTime             INTEGER,
    vlanNewCfgRlTime            INTEGER,
    vlanNewCfgPlTime            Unsigned32,
    vlanNewCfgVlTime            Unsigned32,
    vlanNewCfgOpInfo            INTEGER,
    vlanNewCfgApInfo            INTEGER,
    vlanNewCfgIpv6Lla           DisplayString,
    vlanNewCfgDelete 		INTEGER,
    vlanNewCfgMtuSize           Integer32,
    vlanNewCfgMtuFrag           INTEGER
    }

vlanNewCfgVlanId OBJECT-TYPE
    SYNTAX  Integer32
    MAX-ACCESS  read-only
    STATUS  current
    DESCRIPTION
        "The VLAN identifier,
         Note:This mib is supported only for VX instance of Virtualization."
    ::= { vlanNewCfgTableEntry 1 }

vlanNewCfgVlanName OBJECT-TYPE
    SYNTAX  DisplayString (SIZE(0..32))
    MAX-ACCESS  read-create
    STATUS  current
    DESCRIPTION
        "The VLAN name."
    ::= { vlanNewCfgTableEntry 2 }

vlanNewCfgPorts	OBJECT-TYPE
    SYNTAX  OCTET STRING
    MAX-ACCESS  read-only
    STATUS  current
    DESCRIPTION
        "The port list in the VLAN.  The ports are presented in bitmap format.
         in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
	           0 - The represented port does not belong to the VLAN"
    ::= { vlanNewCfgTableEntry 3 }

vlanNewCfgState	OBJECT-TYPE
    SYNTAX  INTEGER  {
	enabled(2),
	disabled(3),
        unsupported(2147483647)
	}
    MAX-ACCESS  read-create
    STATUS  current
    DESCRIPTION
        "Enable or disable a VLAN"
    ::= { vlanNewCfgTableEntry 4 }

vlanNewCfgAddPort OBJECT-TYPE
    SYNTAX  Integer32
    MAX-ACCESS  read-create
    STATUS  current
    DESCRIPTION
        "The port to be added to the specified VLAN.  A '0' value is 
         returned when read."
    ::= { vlanNewCfgTableEntry 5 }

vlanNewCfgRemovePort OBJECT-TYPE
    SYNTAX  Integer32
    MAX-ACCESS  read-create
    STATUS  current
    DESCRIPTION
        "The port to be removed from the specified VLAN.  A '0'
         value is returned when read."
    ::= { vlanNewCfgTableEntry 6 }

vlanNewCfgDelete OBJECT-TYPE
    SYNTAX  INTEGER  {
        other(1),
        delete(2),
        unsupported(2147483647)
        }
    MAX-ACCESS  read-create
    STATUS  current
    DESCRIPTION
        "This is an action object to create or delete a VLAN.
         other(1) is returned always when read.
         The following values are writable: delete(2)...to delete a VLAN"
    ::= { vlanNewCfgTableEntry 7 }

vlanNewCfgBwmContract OBJECT-TYPE
    SYNTAX  Integer32  
    MAX-ACCESS  read-create
    STATUS  current
    DESCRIPTION
        "Default contract number for the VLAN."
    ::= { vlanNewCfgTableEntry 8 }

vlanNewCfgStg OBJECT-TYPE
    SYNTAX  Integer32  
    MAX-ACCESS  read-create
    STATUS  current
    DESCRIPTION
        "The Spanning Tree Group for the VLAN."
    ::= { vlanNewCfgTableEntry 9 }

vlanNewCfgJumbo	OBJECT-TYPE
    SYNTAX  INTEGER  {
	enabled(2),
	disabled(3),
        unsupported(2147483647)
	}
    MAX-ACCESS  read-create
    STATUS  current
    DESCRIPTION
        "Enable or disable Jumbo frames on a VLAN"
    ::= { vlanNewCfgTableEntry 10 }

vlanNewCfgLearn OBJECT-TYPE
    SYNTAX  INTEGER  {
        enabled(2),
        disabled(3),
        unsupported(2147483647)
        }
    MAX-ACCESS  read-create
    STATUS  current
    DESCRIPTION
        "Enable or disable source mac address learning on a VLAN"
    ::= { vlanNewCfgTableEntry 11 }

vlanNewCfgShared OBJECT-TYPE
    SYNTAX  INTEGER  {
        enabled(2),
        disabled(3),
        unsupported(2147483647)
        }
    MAX-ACCESS  read-create
    STATUS  current
    DESCRIPTION
        "Enable or disable shared property of a VLAN,
         This mib is supported only on VX platform."
    ::= { vlanNewCfgTableEntry 12 }
vlanNewCfgIpv6LlaGen OBJECT-TYPE
    SYNTAX INTEGER {
        enabled(2),
        disabled(3),
        unsupported(2147483647)
    }
    MAX-ACCESS read-create
    STATUS current
    DESCRIPTION
        "Enable/disable IPv6 Link Local Address Generation,
         This mib is supported only on VA and Stand Alone platforms."
    ::= { vlanNewCfgTableEntry 13 }

vlanNewCfgRouterAdv OBJECT-TYPE
    SYNTAX INTEGER {
        enabled(2),
        disabled(3),
        unsupported(2147483647)
    }
    MAX-ACCESS read-create
    STATUS current
    DESCRIPTION
        "Enable/disable router advertisement,
         This mib is supported only on VA and Stand Alone platforms."
    ::= { vlanNewCfgTableEntry 14 }

vlanNewCfgReTransInt OBJECT-TYPE
    SYNTAX Unsigned32 ( 0..4294967295 )
    MAX-ACCESS read-create
    STATUS current
    DESCRIPTION
        "Retransmission interval,
         This mib is supported only on VA and Stand Alone platforms."
    ::= { vlanNewCfgTableEntry 15 }

vlanNewCfgMinIntBwAdv OBJECT-TYPE
    SYNTAX INTEGER ( 3 .. 1800 )
    MAX-ACCESS read-create
    STATUS current
    DESCRIPTION
        "Minimum interval between router advertisements,
         This mib is supported only on VA and Stand Alone platforms."
    ::= { vlanNewCfgTableEntry 16 }

vlanNewCfgMaxIntBwAdv OBJECT-TYPE
    SYNTAX INTEGER ( 4 .. 1800 )
    MAX-ACCESS read-create
    STATUS current
    DESCRIPTION
        "Maximum interval between router advertisements,
         This mib is supported only on VA and Stand Alone platforms."
    ::= { vlanNewCfgTableEntry 17 }

vlanNewCfgMtu OBJECT-TYPE
    SYNTAX INTEGER ( 1200 .. 1500 )
    MAX-ACCESS read-create
    STATUS current
    DESCRIPTION
        "Maximum Transmission Unit. Enter 0 for None,
         This mib is supported only on VA and Stand Alone platforms."
    ::= { vlanNewCfgTableEntry 18 }

vlanNewCfgCurHopLimit OBJECT-TYPE
    SYNTAX INTEGER ( 0 .. 255 )
    MAX-ACCESS read-create
    STATUS current
    DESCRIPTION
        "Current hop limit field,
         This mib is supported only on VA and Stand Alone platforms."
    ::= { vlanNewCfgTableEntry 19 }

vlanNewCfgMFlag OBJECT-TYPE
    SYNTAX INTEGER {
        enabled(2),
        disabled(3),
        unsupported(2147483647)
    }
    MAX-ACCESS read-create
    STATUS current
    DESCRIPTION
        "Enable / Disable Managed address configuration flag,
         This mib is supported only on VA and Stand Alone platforms."
    ::= { vlanNewCfgTableEntry 20 }

vlanNewCfgOFlag OBJECT-TYPE
    SYNTAX INTEGER {
        enabled(2),
        disabled(3),
        unsupported(2147483647)
    }
    MAX-ACCESS read-create
    STATUS current
    DESCRIPTION
        "Enable / Disable Other address configuration flag,
         This mib is supported only on VA and Stand Alone platforms."
    ::= { vlanNewCfgTableEntry 21 }

vlanNewCfgRTime OBJECT-TYPE
    SYNTAX INTEGER ( 0 .. 3600000 )
    MAX-ACCESS read-create
    STATUS current
    DESCRIPTION
        "Reachable time,
         This mib is supported only on VA and Stand Alone platforms."
    ::= { vlanNewCfgTableEntry 22 }

vlanNewCfgRlTime OBJECT-TYPE
    SYNTAX INTEGER ( 0 .. 9000 )
    MAX-ACCESS read-create
    STATUS current
    DESCRIPTION
        "Life Time.Enter 0 for None,
         This mib is supported only on VA and Stand Alone platforms."
    ::= { vlanNewCfgTableEntry 23 }

vlanNewCfgPlTime OBJECT-TYPE
    SYNTAX Unsigned32 ( 0 .. 4294967295 )
    MAX-ACCESS read-create
    STATUS current
    DESCRIPTION
        "Preferred life time,
         This mib is supported only on VA and Stand Alone platforms."
    ::= { vlanNewCfgTableEntry 24 }

vlanNewCfgVlTime OBJECT-TYPE
    SYNTAX Unsigned32 ( 0..4294967295 )
    MAX-ACCESS read-create
    STATUS current
    DESCRIPTION
        "Valid life time,
         This mib is supported only on VA and Stand Alone platforms."
    ::= { vlanNewCfgTableEntry 25 }

vlanNewCfgOpInfo OBJECT-TYPE
    SYNTAX INTEGER {
        enabled(2),
        disabled(3),
        unsupported(2147483647)
    }
    MAX-ACCESS read-create
    STATUS current
    DESCRIPTION
        "Enable / Disable On-link flag in prefix,
         This mib is supported only on VA and Stand Alone platforms."
    ::= { vlanNewCfgTableEntry 26 }


vlanNewCfgApInfo OBJECT-TYPE
    SYNTAX INTEGER {
        enabled(2),
        disabled(3),
        unsupported(2147483647)
    }
    MAX-ACCESS read-create
    STATUS current
    DESCRIPTION
        "Enable / Disable Autonomous address configuration flag in prefix,
         This mib is supported only on VA and Stand Alone platforms."
    ::= { vlanNewCfgTableEntry 27 }

vlanNewCfgIpv6Lla OBJECT-TYPE
    SYNTAX DisplayString (SIZE(0..40))
    MAX-ACCESS  read-create
    STATUS  current
    DESCRIPTION
        "IPV6 Link Local Address,
         This mib is supported only on VA and Stand Alone platforms."
    ::= { vlanNewCfgTableEntry 28 }

vlanNewCfgMtuSize OBJECT-TYPE
    SYNTAX Integer32 ( 1500..9216 )
    MAX-ACCESS read-create
    STATUS current
    DESCRIPTION
        "The VLAN MtuSize,
         This mib is supported only on VA and Stand Alone platforms."
    ::= { vlanNewCfgTableEntry 29 }

vlanNewCfgMtuFrag OBJECT-TYPE
    SYNTAX  INTEGER  {
        enabled(2),
        disabled(3),
        unsupported(2147483647)
        }
    MAX-ACCESS  read-create
    STATUS  current
    DESCRIPTION
        "Enable or disable a VLAN MtuFrag"
    ::= { vlanNewCfgTableEntry 30 }


-- Link Aggregation Control Protocol Group
lacpCurSystemPriority OBJECT-TYPE
    SYNTAX  INTEGER (1..65535)
    MAX-ACCESS  read-only
    STATUS  current
    DESCRIPTION
       "A 2-octet read-write value indicating the priority
        value associated with the Actor's System ID.
        Note:This mib is not supported in vADC instance on Virtualization."
    ::= { lacp 1 }

lacpNewSystemPriority OBJECT-TYPE
    SYNTAX  INTEGER (1..65535)
    MAX-ACCESS  read-write
    STATUS  current
    DESCRIPTION
       "A 2-octet read-write value indicating the priority
        value associated with the Actor's System ID.
        Note:This mib is not supported in vADC instance on Virtualization."
    ::= { lacp 2 }

lacpCurSystemTimeoutTime OBJECT-TYPE
    SYNTAX  INTEGER  {
        short(3),
        long(90),
        unsupported(2147483647)
        }
    MAX-ACCESS  read-only
    STATUS  current
    DESCRIPTION
        "If a port does not receive LACPDUs for Timeout time LACP 
         information pertaining to the port is invalidated.
         Its every 3 sec (short) and every 90 sec (long 3).
         Note:This mib is not supported in vADC instance on Virtualization."
    ::= { lacp 5 }

lacpNewSystemTimeoutTime OBJECT-TYPE
    SYNTAX  INTEGER  {
        short(3),
        long(90),
        unsupported(2147483647)
        }
    MAX-ACCESS  read-write
    STATUS  current
    DESCRIPTION
        "If a port does not receive LACPDUs for Timeout time LACP 
         information pertaining to the port is invalidated.
         Its every 3 sec (short) and every 90 sec (long 3).
         Note:This mib is not supported in vADC instance on Virtualization."
    ::= { lacp 6 }

lacpCurPortCfgTable OBJECT-TYPE
    SYNTAX  SEQUENCE OF LacpCurPortCfgTableEntry
    MAX-ACCESS  not-accessible
    STATUS  current
    DESCRIPTION
        "The table of LACP port configuration.
        Note:This mib is not supported in vADC instance on Virtualization."
    ::= { lacp 7 }

lacpCurPortCfgTableEntry OBJECT-TYPE
    SYNTAX  LacpCurPortCfgTableEntry
    MAX-ACCESS  not-accessible
    STATUS  current
    DESCRIPTION
        "A row in the LACP port configuration table.
        Note:This mib is not supported in vADC instance on Virtualization."
    INDEX  { lacpCurPortCfgTableId }
    ::= { lacpCurPortCfgTable 1 }

LacpCurPortCfgTableEntry ::= SEQUENCE {
    lacpCurPortCfgTableId 	    Integer32,
    lacpCurPortState                INTEGER, 
    lacpCurPortActorPortPriority    INTEGER, 
    lacpCurPortActorAdminKey        INTEGER 
    }

lacpCurPortCfgTableId OBJECT-TYPE
    SYNTAX Integer32
    MAX-ACCESS  read-only
    STATUS  current
    DESCRIPTION
          " LACP port number.
          Note:This mib is not supported in vADC instance on Virtualization."
    ::= { lacpCurPortCfgTableEntry 1 }

lacpCurPortState OBJECT-TYPE
    SYNTAX  INTEGER  {
        off(1),
        active(2),
        passive(3),
        unsupported(2147483647)
        }
    MAX-ACCESS  read-only
    STATUS  current
    DESCRIPTION
        "LACP port state can be one of three states 
         off (Not participating in LACP) 
         Active (Initiates LACPDU updates)
         Passive (Does not initiate LACPDU updates but responds to peer.
         Note:This mib is not supported in vADC instance on Virtualization."
    ::= { lacpCurPortCfgTableEntry 2 }

lacpCurPortActorPortPriority OBJECT-TYPE
    SYNTAX       INTEGER (1..65535)
    MAX-ACCESS       read-only
    STATUS       current
    DESCRIPTION
        "The priority value assigned to this Aggregation Port.
        This 16-bit value is read-only.
        Note:This mib is not supported in vADC instance on Virtualization."
    ::= { lacpCurPortCfgTableEntry 3 }

lacpCurPortActorAdminKey OBJECT-TYPE
    SYNTAX       INTEGER (1..65535)
    MAX-ACCESS       read-only
    STATUS       current
    DESCRIPTION
        "The current administrative value of the Key for the
        Aggregation Port. This is a 16-bit read-only value.
        The meaning of particular Key values is of local
        significance.
        Note:This mib is not supported in vADC instance on Virtualization."
    ::= { lacpCurPortCfgTableEntry 4 }

lacpNewPortCfgTable OBJECT-TYPE
    SYNTAX  SEQUENCE OF LacpNewPortCfgTableEntry
    MAX-ACCESS  not-accessible
    STATUS  current
    DESCRIPTION
        "The table of LACP port configuration.
        Note:This mib is not supported in vADC instance on Virtualization."
    ::= { lacp 8 }

lacpNewPortCfgTableEntry OBJECT-TYPE
    SYNTAX  LacpNewPortCfgTableEntry
    MAX-ACCESS  not-accessible
    STATUS  current
    DESCRIPTION
        "A row in the LACP port configuration table.
        Note:This mib is not supported in vADC instance on Virtualization."
    INDEX  { lacpNewPortCfgTableId }
    ::= { lacpNewPortCfgTable 1 }

LacpNewPortCfgTableEntry ::= SEQUENCE {
    lacpNewPortCfgTableId 	    Integer32,
    lacpNewPortState                INTEGER, 
    lacpNewPortActorPortPriority    INTEGER, 
    lacpNewPortActorAdminKey        INTEGER 
    }

lacpNewPortCfgTableId OBJECT-TYPE
    SYNTAX Integer32
    MAX-ACCESS  read-only
    STATUS  current
    DESCRIPTION
          " LACP port number.
          Note:This mib is not supported in vADC instance on Virtualization."
    ::= { lacpNewPortCfgTableEntry 1 }

lacpNewPortState OBJECT-TYPE
    SYNTAX  INTEGER  {
        off(1),
        active(2),
        passive(3),
        unsupported(2147483647)
        }
    MAX-ACCESS  read-write
    STATUS  current
    DESCRIPTION
        "LACP port state can be one of three states 
         off (Not participating in LACP) 
         Active (Initiates LACPDU updates)
         Passive (Does not initiate LACPDU updates but responds to peer.
         Note:This mib is not supported in vADC instance on Virtualization."
    ::= { lacpNewPortCfgTableEntry 2 }

lacpNewPortActorPortPriority OBJECT-TYPE
    SYNTAX       INTEGER (1..65535)
    MAX-ACCESS       read-write
    STATUS       current
    DESCRIPTION
        "The priority value assigned to this Aggregation Port.
        This 16-bit value is read-write.
        Note:This mib is not supported in vADC instance on Virtualization."
    ::= { lacpNewPortCfgTableEntry 3 }

lacpNewPortActorAdminKey OBJECT-TYPE
    SYNTAX       INTEGER (1..65535)
    MAX-ACCESS       read-write
    STATUS       current
    DESCRIPTION
        "The current administrative value of the Key for the
        Aggregation Port. This is a 16-bit read-write value.
        The meaning of particular Key values is of local
        significance.
        Note:This mib is not supported in vADC instance on Virtualization."
    ::= { lacpNewPortCfgTableEntry 4 }

lacpCurSystemName OBJECT-TYPE
    SYNTAX DisplayString (SIZE (0..31))
    MAX-ACCESS  read-only
    STATUS  current
    DESCRIPTION
        "LACP System Name
        Note:This mib is not supported in vADC instance on Virtualization."
    ::= { lacp 9 }


lacpNewSystemName OBJECT-TYPE
    SYNTAX DisplayString (SIZE (0..31))
    MAX-ACCESS  read-write
    STATUS  current
    DESCRIPTION
        "LACP System Name
        Note:This mib is not supported in vADC instance on Virtualization."
    ::= { lacp 10 }

lacpCurBlockPort OBJECT-TYPE
    SYNTAX  INTEGER {
        enabled(1),
        disabled(2),
        unsupported(2147483647)
        }
    MAX-ACCESS  read-only
    STATUS  current
    DESCRIPTION
        "Current setting for blocking traffic on ports when not in Link Aggregation Group
        Note:This mib is not supported in vADC instance on Virtualization."
    ::= { lacp 11 }

lacpNewBlockPort OBJECT-TYPE
    SYNTAX  INTEGER {
        enabled(1),
        disabled(2),
        unsupported(2147483647)
        }
    MAX-ACCESS  read-write
    STATUS  current
    DESCRIPTION
        "Block(1)/Forward(2) traffic on ports when not in Link Aggregation Group
        Note:This mib is not supported in vADC instance on Virtualization."
    ::= { lacp 12 }


-- Trunk Group Group
trunkGroupTableMaxSize OBJECT-TYPE
    SYNTAX  Integer32
    MAX-ACCESS  read-only
    STATUS  current
    DESCRIPTION
        "The maximum number of entries in trunk group table,
         This mib is not supported on vADC platform."
    ::= { trunkgroup 1 }

trunkGroupCurCfgTable OBJECT-TYPE
    SYNTAX  SEQUENCE OF TrunkGroupCurCfgTableEntry
    MAX-ACCESS  not-accessible
    STATUS  current
    DESCRIPTION
        "The table of trunk group configuration,
         This mib is not supported on vADC platform."
    ::= { trunkgroup 2 }

trunkGroupCurCfgTableEntry OBJECT-TYPE
    SYNTAX  TrunkGroupCurCfgTableEntry
    MAX-ACCESS  not-accessible
    STATUS  current
    DESCRIPTION
        "A row in the trunk group configuration table,
         This mib is not supported on vADC platform."
    INDEX   { trunkGroupCurCfgIndex }
    ::= { trunkGroupCurCfgTable 1 }

TrunkGroupCurCfgTableEntry ::= SEQUENCE {
    trunkGroupCurCfgIndex         Integer32,
    trunkGroupCurCfgPorts         OCTET STRING,
    trunkGroupCurCfgBwmContract   Integer32,
    trunkGroupCurCfgState         INTEGER,
    trunkGroupCurCfgName          DisplayString,
    trunkGroupCurCfgPortCount     Integer32
    }
 
trunkGroupCurCfgIndex OBJECT-TYPE
    SYNTAX  Integer32  
    MAX-ACCESS  read-only
    STATUS  current
    DESCRIPTION
        "The identifier of the trunk group,
         This mib is not supported on vADC platform."
    ::= { trunkGroupCurCfgTableEntry 1 }
 
trunkGroupCurCfgPorts OBJECT-TYPE
    SYNTAX  OCTET STRING
    MAX-ACCESS  read-only
    STATUS  current
    DESCRIPTION
        "The port list in the trunk group. The ports are presented in 
         bitmap format.
 
         in receiving order:
 
             OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the trunk group
                   0 - The represented port does not belong to the trunk group
         This mib is not supported on vADC platform."
    ::= { trunkGroupCurCfgTableEntry 2 }
 
trunkGroupCurCfgState OBJECT-TYPE
    SYNTAX  INTEGER  {
        enable(1),
        disable(2),
        unsupported(2147483647)
        }
    MAX-ACCESS  read-only
    STATUS  current
    DESCRIPTION
        "Enable or disable a trunk group,
         This mib is not supported on vADC platform."
    ::= { trunkGroupCurCfgTableEntry 3 }
 
trunkGroupCurCfgBwmContract OBJECT-TYPE
    SYNTAX  Integer32  
    MAX-ACCESS  read-only
    STATUS  current
    DESCRIPTION
        "Default BW contract of a trunk group,
         This mib is not supported on vADC platform."
    ::= { trunkGroupCurCfgTableEntry 4 }
 
trunkGroupCurCfgName OBJECT-TYPE
    SYNTAX DisplayString (SIZE (0..31))
    MAX-ACCESS read-only
    STATUS current
    DESCRIPTION
        "Name of a trunk group,
         This mib is not supported on vADC platform."
    ::= { trunkGroupCurCfgTableEntry 6 }

trunkGroupCurCfgPortCount OBJECT-TYPE
    SYNTAX  Integer32
    MAX-ACCESS  read-only
    STATUS  current
    DESCRIPTION
        "Number of ports configured in trunk group,
         This mib is not supported on vADC platform."
    ::= { trunkGroupCurCfgTableEntry 7 }


trunkGroupNewCfgTable OBJECT-TYPE
    SYNTAX  SEQUENCE OF TrunkGroupNewCfgTableEntry
    MAX-ACCESS  not-accessible
    STATUS  current
    DESCRIPTION
        "The table of trunk group configuration,
         This mib is not supported on vADC platform."
    ::= { trunkgroup 3 }

trunkGroupNewCfgTableEntry OBJECT-TYPE
    SYNTAX  TrunkGroupNewCfgTableEntry
    MAX-ACCESS  not-accessible
    STATUS  current
    DESCRIPTION
        "A row in the trunk group configuration table,
         This mib is not supported on vADC platform."
    INDEX   { trunkGroupNewCfgIndex }
    ::= { trunkGroupNewCfgTable 1 }

TrunkGroupNewCfgTableEntry ::= SEQUENCE {
    trunkGroupNewCfgIndex          Integer32,
    trunkGroupNewCfgPorts          OCTET STRING,
    trunkGroupNewCfgAddPort        Integer32,
    trunkGroupNewCfgRemovePort     Integer32,
    trunkGroupNewCfgState          INTEGER,
    trunkGroupNewCfgBwmContract    Integer32,
    trunkGroupNewCfgDelete         INTEGER,
    trunkGroupNewCfgName           DisplayString,
    trunkGroupNewCfgPortCount      Integer32
    }
 
trunkGroupNewCfgIndex OBJECT-TYPE
    SYNTAX  Integer32  
    MAX-ACCESS  read-only
    STATUS  current
    DESCRIPTION
        "The identifier of the trunk group,
         This mib is not supported on vADC platform."
    ::= { trunkGroupNewCfgTableEntry 1 }
 
trunkGroupNewCfgPorts OBJECT-TYPE
    SYNTAX  OCTET STRING
    MAX-ACCESS  read-only
    STATUS  current
    DESCRIPTION
        "The port list in the trunk group.  The ports are presented
         in bitmap format.

         in receiving order:

             OCTET 1  OCTET 2  .....
             xxxxxxxx xxxxxxxx ..... 
             ||    || |_ port 8
             ||    ||  
             ||    ||___ port 7
             ||    |____ port 6
             ||      .    .   .
             ||_________ port 1
             |__________ reserved
 
         where x : 1 - The represented port belongs to the trunk group
                   0 - The represented port does not belong to the trunk group
         This mib is not supported on vADC platform."
    ::= { trunkGroupNewCfgTableEntry 2 }
 
trunkGroupNewCfgAddPort OBJECT-TYPE
    SYNTAX  Integer32
    MAX-ACCESS  read-create
    STATUS  current
    DESCRIPTION
        "The port to be added in the trunk group. When read, 0 is returned,
         This mib is not supported on vADC platform."
    ::= { trunkGroupNewCfgTableEntry 3 }

trunkGroupNewCfgRemovePort OBJECT-TYPE
    SYNTAX  Integer32
    MAX-ACCESS  read-create
    STATUS  current
    DESCRIPTION
        "The port to be deleted from the trunk group. when read, 0
	 is returned,
         This mib is not supported on vADC platform."
    ::= { trunkGroupNewCfgTableEntry 4 }

trunkGroupNewCfgState OBJECT-TYPE
    SYNTAX  INTEGER  {
        enable(1),
        disable(2),
        unsupported(2147483647)
        }
    MAX-ACCESS  read-create
    STATUS  current
    DESCRIPTION
        "Enable or disable a trunk group,
         This mib is not supported on vADC platform."
    ::= { trunkGroupNewCfgTableEntry 5 }
 
trunkGroupNewCfgDelete OBJECT-TYPE
    SYNTAX  INTEGER  {
        other(1),
        delete(2),
        unsupported(2147483647)
        }
    MAX-ACCESS  read-create
    STATUS  current
    DESCRIPTION
        "Setting the value to delete(2) will delete the entire
         row. When read, other(1) is returned,
         This mib is not supported on vADC platform."
    ::= { trunkGroupNewCfgTableEntry 6 }

trunkGroupNewCfgBwmContract OBJECT-TYPE
    SYNTAX  Integer32  
    MAX-ACCESS  read-create
    STATUS  current
    DESCRIPTION
        "Default BW contract of a trunk group,
         This mib is not supported on vADC platform."
    ::= { trunkGroupNewCfgTableEntry 7 }

trunkGroupNewCfgName OBJECT-TYPE
    SYNTAX DisplayString (SIZE (0..31))
    MAX-ACCESS read-create
    STATUS current
    DESCRIPTION
        "Name of a trunk group,
         This mib is not supported on vADC platform."
    ::= { trunkGroupNewCfgTableEntry 9 }

trunkGroupNewCfgPortCount OBJECT-TYPE
    SYNTAX  Integer32
    MAX-ACCESS  read-only
    STATUS  current
    DESCRIPTION
        "Number of ports configured in trunk group,
         This mib is not supported on vADC platform."
    ::= { trunkGroupNewCfgTableEntry 10 }


-- Spanning Tree Group Configuration
-- This group specifies the additional configurations that are not
-- covered by the Bridge MIB (RFC 1493).
-- The relative Spanning Tree information can be retrieved or configured
-- using Bridge MIB with an unique community string for each group specified
-- in entLogicalTable of Entity MIB (RFC 2037).
--
stgCurCfgTable OBJECT-TYPE
    SYNTAX SEQUENCE OF StgCurCfgTableEntry
    MAX-ACCESS not-accessible
    STATUS current
    DESCRIPTION
        "The table of Spanning Tree Group configuration,
         This mib is not supported on vADC platform."
    ::= { stgCfg 1 }

stgCurCfgTableEntry OBJECT-TYPE
    SYNTAX StgCurCfgTableEntry
    MAX-ACCESS not-accessible
    STATUS current
    DESCRIPTION
        "Information about a particular Spanning Tree Group configuration,
         This mib is not supported on vADC platform."
    INDEX { stgCurCfgIndex }
    ::= { stgCurCfgTable 1 }

StgCurCfgTableEntry ::= SEQUENCE {
    stgCurCfgIndex           Integer32,
    stgCurCfgState           INTEGER,
    stgCurCfgPriority        INTEGER,
    stgCurCfgBrgHelloTime    INTEGER,
    stgCurCfgBrgForwardDelay INTEGER,
    stgCurCfgBrgMaxAge       INTEGER,
    stgCurCfgAgingTime       INTEGER,
    stgCurCfgVlanBmap        OCTET STRING,
    stgCurCfgUntagPvst       INTEGER,
    stgCurCfgVlanListType    INTEGER,
    stgCurCfgVlanBmap3       OCTET STRING
    }

stgCurCfgIndex OBJECT-TYPE
    SYNTAX Integer32
    MAX-ACCESS read-only
    STATUS current
    DESCRIPTION
        "The identifier of a particular Spanning Tree Group,
         This mib is not supported on vADC platform."
    ::= { stgCurCfgTableEntry 1 }

stgCurCfgState OBJECT-TYPE
    SYNTAX INTEGER {
        on(1),
        off(2),
        unsupported(2147483647)
        }
    MAX-ACCESS read-only
    STATUS current
    DESCRIPTION
        "Turn on of off Spanning Tree operation of a particular Spanning
         Tree Group,
         This mib is not supported on vADC platform."
    ::= { stgCurCfgTableEntry 2 }

stgCurCfgPriority OBJECT-TYPE
    SYNTAX  INTEGER (0..65535)
    MAX-ACCESS  read-only
    STATUS  current
    DESCRIPTION
        "The value of the write-able portion of the Bridge ID, i.e., the first
         two octets of the (8 octet long) Bridge ID,
         This mib is not supported on vADC platform."
    ::= { stgCurCfgTableEntry 5 }

stgCurCfgBrgHelloTime OBJECT-TYPE
    SYNTAX  INTEGER (1..10)
    MAX-ACCESS  read-only
    STATUS  current
    DESCRIPTION
        "The value in seconds that all bridges use for HelloTime when this 
         bridge is acting as the root,
         This mib is not supported on vADC platform."
    ::= { stgCurCfgTableEntry 6 }

stgCurCfgBrgForwardDelay OBJECT-TYPE
    SYNTAX  INTEGER (4..30)
    MAX-ACCESS  read-only
    STATUS  current
    DESCRIPTION
        "The value in seconds that all bridges use for ForwardDelay when this 
         bridge is acting as the root,
         This mib is not supported on vADC platform."
    ::= { stgCurCfgTableEntry 7 }

stgCurCfgBrgMaxAge OBJECT-TYPE
    SYNTAX  INTEGER (6..40)
    MAX-ACCESS  read-only
    STATUS  current
    DESCRIPTION
        "The value in seconds that all bridges use for MaxAge when this bridge
         is acting as the root,
         This mib is not supported on vADC platform."
    ::= { stgCurCfgTableEntry 8 }

stgCurCfgAgingTime OBJECT-TYPE
    SYNTAX  INTEGER (0..65535)
    MAX-ACCESS  read-only
    STATUS  current
    DESCRIPTION
        "The timeout period in seconds for aging out dynamically learned 
         forwarding information,
         This mib is not supported on vADC platform."
    ::= { stgCurCfgTableEntry 9 }

stgCurCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4096.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree
         This mib is not supported on vADC platform."
    ::= { stgCurCfgTableEntry 10 }

stgCurCfgUntagPvst OBJECT-TYPE
    SYNTAX INTEGER {
        enabled(1),
        disabled(2),
        unsupported(2147483647)
        }
    MAX-ACCESS read-only
    STATUS current
    DESCRIPTION
        "Enable/Disable sending PVST frames on untagged ports,
         This mib is not supported on vADC platform."
    ::= { stgCurCfgTableEntry 11 }

stgCurCfgVlanListType OBJECT-TYPE
    SYNTAX INTEGER {
        default(1),
        listall(2),
        unsupported(2147483647)
        }
    MAX-ACCESS read-only
    STATUS current
    DESCRIPTION
        "Default or ListAll list available vlan or entire vlan range,
         This mib is not supported on vADC platform."
    ::= { stgCurCfgTableEntry 12 }

stgCurCfgVlanBmap3 OBJECT-TYPE
    SYNTAX  OCTET STRING (SIZE(0..512))
    MAX-ACCESS  read-only
    STATUS  current
    DESCRIPTION
        "The vlans applied to the spanning tree group.  The vlans are
         presented in bitmap format. This string displays vlan number
         from 1 to 4096.

         in receiving order:

             OCTET 1  OCTET 2  .....
             xxxxxxxx xxxxxxxx .....
             ||    || |_ vlan 9
             ||    ||
             ||    ||___ vlan 8
             ||    |____ vlan 7
             ||      .    .   .
             ||_________ vlan 2
             |__________ vlan 1 (as index to stgCurCfgTable)

         where x : 1 - The represented vlan applied to the spanning tree.
                   0 - The represented vlan not applied to the spanning tree
         This mib is not supported on vADC platform."
    ::= { stgCurCfgTableEntry 13 }

stgNewCfgTable OBJECT-TYPE
    SYNTAX SEQUENCE OF StgNewCfgTableEntry
    MAX-ACCESS not-accessible
    STATUS current
    DESCRIPTION
        "The table of Spanning Tree Groups configuration in the new_config,
         This mib is not supported on vADC platform."
    ::= { stgCfg 2 }

stgNewCfgTableEntry OBJECT-TYPE
    SYNTAX StgNewCfgTableEntry
    MAX-ACCESS not-accessible
    STATUS current
    DESCRIPTION
        "Information about a particular Spanning Tree Group configuration,
         This mib is not supported on vADC platform."
    INDEX { stgNewCfgIndex }
    ::= { stgNewCfgTable 1 }

StgNewCfgTableEntry ::= SEQUENCE {
    stgNewCfgIndex           Integer32,
    stgNewCfgState           INTEGER,
    stgNewCfgDefaultCfg      INTEGER,
    stgNewCfgAddVlan         Integer32,
    stgNewCfgRemoveVlan      Integer32,
    stgNewCfgPriority        INTEGER,
    stgNewCfgBrgHelloTime    INTEGER,
    stgNewCfgBrgForwardDelay INTEGER,
    stgNewCfgBrgMaxAge       INTEGER,
    stgNewCfgAgingTime       INTEGER,
    stgNewCfgVlanBmap        OCTET STRING,
    stgNewCfgUntagPvst       INTEGER,
    stgNewCfgVlanListType    INTEGER,
    stgNewCfgVlanBmap3        OCTET STRING
    }

stgNewCfgIndex  OBJECT-TYPE
    SYNTAX Integer32
    MAX-ACCESS read-only
    STATUS current
    DESCRIPTION
        "The identifier of a particular Spanning Tree Group,
         This mib is not supported on vADC platform."
    ::= { stgNewCfgTableEntry 1 }

stgNewCfgState OBJECT-TYPE
    SYNTAX INTEGER {
        on(1),
        off(2),
        unsupported(2147483647)
        }
    MAX-ACCESS read-write
    STATUS current
    DESCRIPTION
        "Turn on of off Spanning Tree operation of a particular Spanning
         Tree Group,
         This mib is not supported on vADC platform."
    ::= { stgNewCfgTableEntry 2 }

stgNewCfgDefaultCfg OBJECT-TYPE
    SYNTAX INTEGER {
        default-config(1),
        unsupported(2147483647)
        }
    MAX-ACCESS read-write
    STATUS current
    DESCRIPTION
        "Setting the value to default-config(1) will set the default
         configuration as recommended by IEEE 802.1D for a particular
         Spanning Tree Group.  default-config (1) is always returned 
	 When read, but it does not mean anything,
         This mib is not supported on vADC platform."
    ::= { stgNewCfgTableEntry 3 }

stgNewCfgAddVlan OBJECT-TYPE
    SYNTAX  Integer32
    MAX-ACCESS  read-write
    STATUS  current
    DESCRIPTION
        "The vlan to be added to the specified Spanning Tree Group.  A 
         '0' value is returned when read,
         This mib is not supported on vADC platform."
    ::= {stgNewCfgTableEntry 4 }

stgNewCfgRemoveVlan OBJECT-TYPE
    SYNTAX  Integer32
    MAX-ACCESS  read-write
    STATUS  current
    DESCRIPTION
        "The vlan to be removed from the specified Spanning Tree Group.
         A '0' value is returned when read,
         This mib is not supported on vADC platform."
    ::= { stgNewCfgTableEntry 5 }

stgNewCfgPriority OBJECT-TYPE
    SYNTAX  INTEGER (0..65535)
    MAX-ACCESS  read-write
    STATUS  current
    DESCRIPTION
        "The value of the write-able portion of the Bridge ID, i.e., the first
         two octets of the (8 octet long) Bridge ID,
         This mib is not supported on vADC platform."
    ::= { stgNewCfgTableEntry 8 }

stgNewCfgBrgHelloTime OBJECT-TYPE
    SYNTAX  INTEGER (1..10)
    MAX-ACCESS  read-write
    STATUS  current
    DESCRIPTION
        "The value in seconds that all bridges use for HelloTime when this 
         bridge is acting as the root,
         This mib is not supported on vADC platform."
    ::= { stgNewCfgTableEntry 9 }

stgNewCfgBrgForwardDelay OBJECT-TYPE
    SYNTAX  INTEGER (4..30)
    MAX-ACCESS  read-write
    STATUS  current
    DESCRIPTION
        "The value in seconds that all bridges use for ForwardDelay when this 
         bridge is acting as the root,
         This mib is not supported on vADC platform."
    ::= { stgNewCfgTableEntry 10 }

stgNewCfgBrgMaxAge OBJECT-TYPE
    SYNTAX  INTEGER (6..40)
    MAX-ACCESS  read-write
    STATUS  current
    DESCRIPTION
        "The value in seconds that all bridges use for MaxAge when this bridge
         is acting as the root,
         This mib is not supported on vADC platform."
    ::= { stgNewCfgTableEntry 11 }

stgNewCfgAgingTime OBJECT-TYPE
    SYNTAX  INTEGER (0..65535)
    MAX-ACCESS  read-write
    STATUS  current
    DESCRIPTION
        "The timeout period in seconds for aging out dynamically learned 
         forwarding information,
         This mib is not supported on vADC platform."
    ::= { stgNewCfgTableEntry 12 }

stgNewCfgVlanBmap OBJECT-TYPE
    SYNTAX  OCTET STRING (SIZE(0..512)) 
    MAX-ACCESS  read-only
    STATUS  current
    DESCRIPTION
	"The vlans applied to the spanning tree group.  The vlans are 
         presented in bitmap format. This string displays vlan number
	 from 1 to 4096.

	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1 (as index to stgCurCfgTable)

         where x : 1 - The represented vlan applied to the spanning tree. 
		   0 - The represented vlan not applied to the spanning tree
         This mib is not supported on vADC platform."
    ::= { stgNewCfgTableEntry 13 }

stgNewCfgUntagPvst OBJECT-TYPE
    SYNTAX INTEGER {
        enabled(1),
        disabled(2),
        unsupported(2147483647)
        }
    MAX-ACCESS read-create
    STATUS current
    DESCRIPTION
        "Enable/Disable sending PVST frames on untagged ports,
         This mib is not supported on vADC platform."
    ::= { stgNewCfgTableEntry 14 }

stgNewCfgVlanListType OBJECT-TYPE
    SYNTAX INTEGER {
        default(1),
        listall(2),
        unsupported(2147483647)
        }
    MAX-ACCESS read-create
    STATUS current
    DESCRIPTION
        "Default or ListAll list available vlan or entire vlan range,
         This mib is not supported on vADC platform."
    ::= { stgNewCfgTableEntry 15 }

stgNewCfgVlanBmap3 OBJECT-TYPE
    SYNTAX  OCTET STRING (SIZE(0..512))
    MAX-ACCESS  read-only
    STATUS  current
    DESCRIPTION
        "The vlans applied to the spanning tree group.  The vlans are
         presented in bitmap format. This string displays vlan number
         from 1 to 4096.

         in receiving order:

             OCTET 1  OCTET 2  .....
             xxxxxxxx xxxxxxxx .....
             ||    || |_ vlan 9
             ||    ||
             ||    ||___ vlan 8
             ||    |____ vlan 7
             ||      .    .   .
             ||_________ vlan 2
             |__________ vlan 1 (as index to stgCurCfgTable)

         where x : 1 - The represented vlan applied to the spanning tree.
                   0 - The represented vlan not applied to the spanning tree,
         This mib is not supported on vADC platform."
    ::= { stgNewCfgTableEntry 16 }

stgCurCfgPortTable OBJECT-TYPE
    SYNTAX SEQUENCE OF StgCurCfgPortTableEntry
    MAX-ACCESS not-accessible
    STATUS current
    DESCRIPTION
        "The table of Spanning Tree Group port configuration in the
         current_config,
         This mib is not supported on vADC platform."
    ::= { stgCfg 3 }

stgCurCfgPortTableEntry OBJECT-TYPE
    SYNTAX StgCurCfgPortTableEntry
    MAX-ACCESS not-accessible
    STATUS current
    DESCRIPTION
        "Information about port configuration of a particular Spanning Tree
         Group,
         This mib is not supported on vADC platform."
    INDEX { stgCurCfgStgIndex, stgCurCfgPortIndex }
    ::= { stgCurCfgPortTable 1 }

StgCurCfgPortTableEntry ::= SEQUENCE {
    stgCurCfgStgIndex      Integer32,
    stgCurCfgPortIndex     Integer32,
    stgCurCfgPortPriority  INTEGER,
    stgCurCfgPortPathCost  Integer32,
    stgCurCfgPortLink      INTEGER,
    stgCurCfgPortEdge      INTEGER,
    stgCurCfgPortState     INTEGER,
    stgCurCfgBlockBPDU  INTEGER
    }

stgCurCfgStgIndex OBJECT-TYPE
    SYNTAX Integer32
    MAX-ACCESS read-only
    STATUS current
    DESCRIPTION
        "The identifier of a particular Spanning Tree Group,
         This mib is not supported on vADC platform."
    ::= { stgCurCfgPortTableEntry 1 }

stgCurCfgPortIndex OBJECT-TYPE
    SYNTAX Integer32
    MAX-ACCESS read-only
    STATUS current
    DESCRIPTION
        "The port identifier of a particular Spanning Tree Group,
         This mib is not supported on vADC platform."
    ::= { stgCurCfgPortTableEntry 2 }

stgCurCfgPortState OBJECT-TYPE
    SYNTAX INTEGER {
        on(1),
        off(2),
        unsupported(2147483647)
        }
    MAX-ACCESS read-only
    STATUS current
    DESCRIPTION
        "Turn on of off Spanning Tree operation of a particular port of a
         Spanning Tree Group,
         This mib is not supported on vADC platform."
    ::= { stgCurCfgPortTableEntry 3 }

stgCurCfgPortPriority OBJECT-TYPE
    SYNTAX INTEGER (0..255)
    MAX-ACCESS read-only
    STATUS current
    DESCRIPTION
        "The value of the priority field which is contained in the first 
         (in network byte order) octet of the (2 octet long) Port ID,
         This mib is not supported on vADC platform."
    ::= { stgCurCfgPortTableEntry 4 }

stgCurCfgPortPathCost OBJECT-TYPE
    SYNTAX Integer32 
    MAX-ACCESS read-only
    STATUS current
    DESCRIPTION
       "The contribution of this port to the path cost of paths towards the 
        spanning tree root which include this port (if MSTP/RSTP is enabled
        range is (0..200000000) else range is (0..65535) ),
         This mib is not supported on vADC platform."
    ::= { stgCurCfgPortTableEntry 5 }

stgCurCfgPortLink OBJECT-TYPE
    SYNTAX INTEGER {
        auto(1),
        p2p(2),
        shared(3),
        unsupported(2147483647)
        }
    MAX-ACCESS read-only
    STATUS current
    DESCRIPTION
        "The type of the port link,
         This mib is not supported on vADC platform."
    ::= { stgCurCfgPortTableEntry 6 }

stgCurCfgPortEdge OBJECT-TYPE
    SYNTAX INTEGER {
        enabled(1),
        disabled(2),
        unsupported(2147483647)
        }
    MAX-ACCESS read-only
    STATUS current
    DESCRIPTION
        "The state of port edge,
         This mib is not supported on vADC platform."
    ::= { stgCurCfgPortTableEntry 7 }

stgCurCfgBlockBPDU OBJECT-TYPE
    SYNTAX INTEGER {
        enabled(1),
        disabled(2),
        unsupported(2147483647)
        }
    MAX-ACCESS read-only
    STATUS current
    DESCRIPTION
        "Enable/Disable forwarding BPDUs on STG off. To 'enable' this,
         STG and Port's Spanning Tree should be in 'off' state,
         This mib is not supported on vADC platform."
    ::= { stgCurCfgPortTableEntry 8 }

stgNewCfgPortTable OBJECT-TYPE
    SYNTAX SEQUENCE OF StgNewCfgPortTableEntry
    MAX-ACCESS not-accessible
    STATUS current
    DESCRIPTION
        "The table of Spanning Tree Group port configuration in the
         new_config,
         This mib is not supported on vADC platform."
    ::= { stgCfg 4 }

stgNewCfgPortTableEntry OBJECT-TYPE
    SYNTAX StgNewCfgPortTableEntry
    MAX-ACCESS not-accessible
    STATUS current
    DESCRIPTION
        "Information about port configuration of a particular Spanning Tree
         Group,
         This mib is not supported on vADC platform."
    INDEX { stgNewCfgStgIndex, stgNewCfgPortIndex }
    ::= { stgNewCfgPortTable 1 }

StgNewCfgPortTableEntry ::= SEQUENCE {
    stgNewCfgStgIndex      Integer32,
    stgNewCfgPortIndex     Integer32,
    stgNewCfgPortPriority  INTEGER,
    stgNewCfgPortPathCost  Integer32,
    stgNewCfgPortLink      INTEGER,
    stgNewCfgPortEdge      INTEGER,
    stgNewCfgPortState     INTEGER,
    stgNewCfgBlockBPDU     INTEGER
    }

stgNewCfgStgIndex OBJECT-TYPE
    SYNTAX Integer32
    MAX-ACCESS read-only
    STATUS current
    DESCRIPTION
        "The identifier of a particular Spanning Tree Group,
         This mib is not supported on vADC platform."
    ::= { stgNewCfgPortTableEntry 1 }

stgNewCfgPortIndex OBJECT-TYPE
    SYNTAX Integer32
    MAX-ACCESS read-only
    STATUS current
    DESCRIPTION
        "The port identifier of a particular Spanning Tree Group,
         This mib is not supported on vADC platform."
    ::= { stgNewCfgPortTableEntry 2 }

stgNewCfgPortState OBJECT-TYPE
    SYNTAX INTEGER {
        on(1),
        off(2),
        unsupported(2147483647)
        }
    MAX-ACCESS read-create
    STATUS current
    DESCRIPTION
        "Turn on of off Spanning Tree operation of a particular port of a
         Spanning Tree Group,
         This mib is not supported on vADC platform."
    ::= { stgNewCfgPortTableEntry 3 }

stgNewCfgPortPriority OBJECT-TYPE
    SYNTAX INTEGER (0..255)
    MAX-ACCESS read-create
    STATUS current
    DESCRIPTION
        "The value of the priority field which is contained in the first 
         (in network byte order) octet of the (2 octet long) Port ID,
         This mib is not supported on vADC platform."
    ::= { stgNewCfgPortTableEntry 4 }

stgNewCfgPortPathCost OBJECT-TYPE
    SYNTAX  Integer32 
    MAX-ACCESS read-create
    STATUS current
    DESCRIPTION
       "The contribution of this port to the path cost of paths towards the 
        spanning tree root which include this port (if MSTP/RSTP is enabled
        range is (0..200000000) else range is (0..65535) ),
         This mib is not supported on vADC platform."
    ::= { stgNewCfgPortTableEntry 5 }

stgNewCfgPortLink OBJECT-TYPE
    SYNTAX INTEGER {
        auto(1),
        p2p(2),
        shared(3),
        unsupported(2147483647)
        }
    MAX-ACCESS read-create 
    STATUS current
    DESCRIPTION
        "The type of the port link,
         This mib is not supported on vADC platform."
    ::= { stgNewCfgPortTableEntry 6 }

stgNewCfgPortEdge OBJECT-TYPE
    SYNTAX INTEGER {
        enabled(1),
        disabled(2),
        unsupported(2147483647)
        }
    MAX-ACCESS read-create 
    STATUS current
    DESCRIPTION
        "The state of port edge,
         This mib is not supported on vADC platform."
    ::= { stgNewCfgPortTableEntry 7 }

stgNewCfgBlockBPDU OBJECT-TYPE
    SYNTAX INTEGER {
        enabled(1),
        disabled(2),
        unsupported(2147483647)
        }
    MAX-ACCESS read-create
    STATUS current
    DESCRIPTION
        "Enable/Disable forwarding BPDUs on STG off. To 'enable' this,
         STG and Port's Spanning Tree should be in 'off' state,
         This mib is not supported on vADC platform."
    ::= { stgNewCfgPortTableEntry 8 }

stgVlanCurCfgTable OBJECT-TYPE
    SYNTAX  SEQUENCE OF StgVlanCurCfgTableEntry
    MAX-ACCESS  not-accessible
    STATUS  current
    DESCRIPTION
        "The table of All VLANs supported."
    ::= { vlan 5 }

stgVlanCurCfgTableEntry OBJECT-TYPE
    SYNTAX  StgVlanCurCfgTableEntry
    MAX-ACCESS  not-accessible
    STATUS  current
    DESCRIPTION
        "A row in the VLAN configuration table."
    INDEX  { stgVlanCurCfgVlanId }
    ::= { stgVlanCurCfgTable 1 }

StgVlanCurCfgTableEntry ::= SEQUENCE {
    stgVlanCurCfgVlanId            Integer32,
    stgVlanCurCfgVlanName          DisplayString
    }

stgVlanCurCfgVlanId OBJECT-TYPE
    SYNTAX  Integer32
    MAX-ACCESS  read-only
    STATUS  current
    DESCRIPTION
        "The VLAN identifier."
    ::= { stgVlanCurCfgTableEntry 1 }

stgVlanCurCfgVlanName OBJECT-TYPE
    SYNTAX  DisplayString (SIZE(0..32))
    MAX-ACCESS  read-only
    STATUS  current
    DESCRIPTION
        "The VLAN name."
    ::= { stgVlanCurCfgTableEntry 2 }

stgVlanNewCfgTable OBJECT-TYPE
    SYNTAX  SEQUENCE OF StgVlanNewCfgTableEntry
    MAX-ACCESS  not-accessible
    STATUS  current
    DESCRIPTION
        "The table of All VLANs supported."
    ::= { vlan 6 }

stgVlanNewCfgTableEntry OBJECT-TYPE
    SYNTAX  StgVlanNewCfgTableEntry
    MAX-ACCESS  not-accessible
    STATUS  current
    DESCRIPTION
        "A row in the VLAN configuration table."
    INDEX  { stgVlanNewCfgVlanId }
    ::= { stgVlanNewCfgTable 1 }

StgVlanNewCfgTableEntry ::= SEQUENCE {
    stgVlanNewCfgVlanId            Integer32,
    stgVlanNewCfgVlanName          DisplayString
    }

stgVlanNewCfgVlanId OBJECT-TYPE
    SYNTAX  Integer32
    MAX-ACCESS  read-only
    STATUS  current
    DESCRIPTION
        "The VLAN identifier."
    ::= { stgVlanNewCfgTableEntry 1 }

stgVlanNewCfgVlanName OBJECT-TYPE
    SYNTAX  DisplayString (SIZE(0..32))
    MAX-ACCESS  read-only
    STATUS  current
    DESCRIPTION
        "The VLAN name."
    ::= { stgVlanNewCfgTableEntry 2 }


-- Complete Port Mirroring 
pmCurCfgPortMirrState OBJECT-TYPE
    SYNTAX  INTEGER {
	enabled(1),
	disabled(2),
        unsupported(2147483647)
	}
    MAX-ACCESS  read-only
    STATUS  current
    DESCRIPTION
        "The state of port-based port mirroring.
        Note:This mib is not supported for VX instance of virtualization."
    ::= { mirrPortMirr 1 }
 
pmNewCfgPortMirrState OBJECT-TYPE
    SYNTAX  INTEGER {
	enabled(1),
	disabled(2),
        unsupported(2147483647)
        }
    MAX-ACCESS  read-write
    STATUS  current
    DESCRIPTION
        "The state of port-based port mirroring.
        Note:This mib is not supported for VX instance of virtualization."
    ::= { mirrPortMirr 2 }

pmCurCfgPortMonitorTable OBJECT-TYPE
    SYNTAX  SEQUENCE OF PmCurCfgPortMonitorEntry
    MAX-ACCESS  not-accessible
    STATUS  current
    DESCRIPTION
        "The table of monitoring ports.
        Note:This mib is not supported for VX instance of virtualization."
    ::= { mirrPortMirr 3 }

pmCurCfgPortMonitorEntry OBJECT-TYPE
    SYNTAX  PmCurCfgPortMonitorEntry
    MAX-ACCESS  not-accessible
    STATUS  current
    DESCRIPTION
        "A row in the monitoring port table.
        Note:This mib is not supported for VX instance of virtualization."
    INDEX   { pmCurCfgPmirrMoniPortIndex, pmCurCfgPmirrMirrPortIndex }
    ::= { pmCurCfgPortMonitorTable 1 }

PmCurCfgPortMonitorEntry ::= SEQUENCE {
    pmCurCfgPmirrMoniPortIndex       Integer32,
    pmCurCfgPmirrMirrPortIndex       Integer32,
    pmCurCfgPmirrDirection           INTEGER,
    pmCurCfgPmirrPortVlansBmap       OCTET STRING
    }

pmCurCfgPmirrMoniPortIndex OBJECT-TYPE
    SYNTAX  Integer32
    MAX-ACCESS  read-only
    STATUS  current
    DESCRIPTION
        "The monitoring port number.
        Note:This mib is not supported for VX instance of virtualization." 
    ::= { pmCurCfgPortMonitorEntry 1 }

pmCurCfgPmirrMirrPortIndex OBJECT-TYPE 
    SYNTAX  Integer32 
    MAX-ACCESS  read-only 
    STATUS  current 
    DESCRIPTION 
        "The mirrored port number
        Note:This mib is not supported for VX instance of virtualization." 
    ::= { pmCurCfgPortMonitorEntry 2 }

pmCurCfgPmirrDirection OBJECT-TYPE
    SYNTAX  INTEGER {
	in(1),
	out(2),
	both(3),
        unsupported(2147483647)
        }
    MAX-ACCESS  read-only
    STATUS  current
    DESCRIPTION
        "The type of traffic to be monitored with respect to the
         mirrored port.
         Note:This mib is not supported for VX instance of virtualization."
    ::= { pmCurCfgPortMonitorEntry 3 }

pmCurCfgPmirrPortVlansBmap	OBJECT-TYPE
    SYNTAX  OCTET STRING
    MAX-ACCESS  read-only
    STATUS  current
    DESCRIPTION
        "The mirrored VLANs (1-4096) list for the port. The VLANs are presented in bitmap format.
	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented VLAN is being mirrored.
		   0 - The represented VLAN is not being mirrored.
         Note: When all octets are zero - all vlan(s) traffic is 
               being for the port
         Note2:This mib is not supported for VX instance of virtualization."
    ::= { pmCurCfgPortMonitorEntry 6 }

pmNewCfgPortMonitorTable OBJECT-TYPE
    SYNTAX  SEQUENCE OF PmNewCfgPortMonitorEntry
    MAX-ACCESS  not-accessible
    STATUS  current
    DESCRIPTION
        "The table of monitoring ports.
        Note:This mib is not supported for VX instance of virtualization."
    ::= { mirrPortMirr 4 }

pmNewCfgPortMonitorEntry OBJECT-TYPE
    SYNTAX  PmNewCfgPortMonitorEntry
    MAX-ACCESS  not-accessible
    STATUS  current
    DESCRIPTION
        "A row in the monitoring port table.
        Note:This mib is not supported for VX instance of virtualization."
    INDEX   { pmNewCfgPmirrMoniPortIndex, pmNewCfgPmirrMirrPortIndex }
    ::= { pmNewCfgPortMonitorTable 1 }

PmNewCfgPortMonitorEntry ::= SEQUENCE {
    pmNewCfgPmirrMoniPortIndex          Integer32,
    pmNewCfgPmirrMirrPortIndex          Integer32,
    pmNewCfgPmirrDirection              INTEGER,
    pmNewCfgPmirrDelete                 INTEGER,
    pmNewCfgAddVlan 			Integer32,
    pmNewCfgRemoveVlan			Integer32,
    pmNewCfgPmirrPortVlansBmap         OCTET STRING
    }

pmNewCfgPmirrMoniPortIndex OBJECT-TYPE
    SYNTAX  Integer32
    MAX-ACCESS  read-only
    STATUS  current
    DESCRIPTION
        "The monitoring port number.
        Note:This mib is not supported for VX instance of virtualization." 
    ::= { pmNewCfgPortMonitorEntry 1 }

pmNewCfgPmirrMirrPortIndex OBJECT-TYPE 
    SYNTAX  Integer32 
    MAX-ACCESS  read-only 
    STATUS  current 
    DESCRIPTION 
        "The mirrored port number
        Note:This mib is not supported for VX instance of virtualization." 
    ::= { pmNewCfgPortMonitorEntry 2 }

pmNewCfgPmirrDirection OBJECT-TYPE
    SYNTAX  INTEGER {
	in(1),
	out(2),
	both(3),
        unsupported(2147483647)
        }
    MAX-ACCESS  read-create
    STATUS  current
    DESCRIPTION
        "The type of traffic to be monitored with respect to the
         mirrored port.
         Note:This mib is not supported for VX instance of virtualization."
    ::= { pmNewCfgPortMonitorEntry 3 }

pmNewCfgPmirrDelete OBJECT-TYPE
    SYNTAX  INTEGER  {
        other(1),
        delete(2),
        unsupported(2147483647)
        }
    MAX-ACCESS  read-create
    STATUS  current
    DESCRIPTION
        "Setting the value to delete(2) will delete the entire
         row. When read, other(1) is returned.
         Note:This mib is not supported for VX instance of virtualization."
    ::= { pmNewCfgPortMonitorEntry 4 }

pmNewCfgAddVlan OBJECT-TYPE
    SYNTAX  Integer32
    MAX-ACCESS  read-create
    STATUS  current
    DESCRIPTION
        "The VLAN whose traffic is to be mirrored for this port. 
         A '0' value is returned when read.
         Note:This mib is not supported for VX instance of virtualization."
    ::= { pmNewCfgPortMonitorEntry 7 }

pmNewCfgRemoveVlan OBJECT-TYPE		
    SYNTAX  Integer32
    MAX-ACCESS  read-create
    STATUS  current
    DESCRIPTION
        "The VLAN whose traffic will no longer to be mirrored. 
         A '0' value is returned when read.
         Note:This mib is not supported for VX instance of virtualization."
    ::= { pmNewCfgPortMonitorEntry 8 }

pmNewCfgPmirrPortVlansBmap	OBJECT-TYPE
    SYNTAX  OCTET STRING
    MAX-ACCESS  read-only
    STATUS  current
    DESCRIPTION
        "The mirrored VLANs(1-4096) list for the port. The VLANs are presented in bitmap format.
	 in receiving order:

	     OCTET 1  OCTET 2  .....
             xxxxxxxx xxxxxxxx ..... 
             ||    || |_ vlan 9
             ||    ||  
             ||    ||___ vlan 8
             ||    |____ vlan 7
             ||      .    .   .
             ||_________ vlan 2
             |__________ vlan 1

         where x : 1 - The represented VLAN is being mirrored.
		   0 - The represented VLAN is not being mirrored.
         Note: All octets are zero means all vlan(s) traffic is 
               being mirrored for the port
         Note:This mib is not supported for VX instance of virtualization."
    ::= { pmNewCfgPortMonitorEntry 9 }

-- MST Configuration 

mstCurCfgState	OBJECT-TYPE
    SYNTAX  INTEGER  {
	enabled(2),
	disabled(3),
        unsupported(2147483647)
	}
    MAX-ACCESS  read-only
    STATUS  current
    DESCRIPTION
        "Enable or disable MSTP/RSTP
        Note:This mib is not supported in vADC instance on Virtualization."
    ::= { mstGeneralCfg 1 }

mstNewCfgState	OBJECT-TYPE
    SYNTAX  INTEGER  {
	enabled(2),
	disabled(3),
        unsupported(2147483647)
	}
    MAX-ACCESS  read-write
    STATUS  current
    DESCRIPTION
        "Enable or disable MSTP/RSTP
        Note:This mib is not supported in vADC instance on Virtualization."
    ::= { mstGeneralCfg 2 }

mstCurCfgRegionName OBJECT-TYPE
   SYNTAX  DisplayString (SIZE (0..32))
   MAX-ACCESS  read-only
   STATUS  current
   DESCRIPTION
      "The Name for the Region's configuration.
      Note:This mib is not supported in vADC instance on Virtualization."
   ::= { mstGeneralCfg 3 } 

mstNewCfgRegionName OBJECT-TYPE
   SYNTAX  DisplayString (SIZE (0..32))
   MAX-ACCESS  read-write
   STATUS  current
   DESCRIPTION
      "The Name for the Region's configuration.
      Note:This mib is not supported in vADC instance on Virtualization."
   ::= { mstGeneralCfg 4 } 

mstCurCfgRegionVersion OBJECT-TYPE
    SYNTAX  INTEGER  (0..65535)
    MAX-ACCESS  read-only
    STATUS  current
    DESCRIPTION
        "Version of the MST Region.
        Note:This mib is not supported in vADC instance on Virtualization."
    ::= { mstGeneralCfg 5 }

mstNewCfgRegionVersion OBJECT-TYPE
    SYNTAX  INTEGER  (0..65535)
    MAX-ACCESS  read-write
    STATUS  current
    DESCRIPTION
        "Version of the MST Region.
        Note:This mib is not supported in vADC instance on Virtualization."
    ::= { mstGeneralCfg 6 }

mstCurCfgMaxHopCount OBJECT-TYPE
    SYNTAX  INTEGER  (4..60)
    MAX-ACCESS  read-only
    STATUS  current
    DESCRIPTION
        "Indicates the maximum hop count value.
        Note:This mib is not supported in vADC instance on Virtualization."
    ::= { mstGeneralCfg 7 }

mstNewCfgMaxHopCount OBJECT-TYPE
    SYNTAX  INTEGER  (4..60)
    MAX-ACCESS  read-write
    STATUS  current
    DESCRIPTION
        "Indicates the maximum hop count value.
        Note:This mib is not supported in vADC instance on Virtualization."
    ::= { mstGeneralCfg 8 }

mstCurCfgStpMode OBJECT-TYPE
    SYNTAX  INTEGER  {
	mstp(1),
	rstp(2),
        unsupported(2147483647)
	}
    MAX-ACCESS  read-only
    STATUS  current
    DESCRIPTION
        "The version of Spanning Tree Protocal the bridge is currently 
         running.
         Note:This mib is not supported in vADC instance on Virtualization."
    ::= { mstGeneralCfg 9 }

mstNewCfgStpMode OBJECT-TYPE
    SYNTAX  INTEGER  {
	mstp(1),
	rstp(2),
        unsupported(2147483647)
	}
    MAX-ACCESS  read-write
    STATUS  current
    DESCRIPTION
        "The version of Spanning Tree Protocal the bridge is currently 
         running.
         Note:This mib is not supported in vADC instance on Virtualization."
    ::= { mstGeneralCfg 10 }

mstCistDefaultCfg OBJECT-TYPE
    SYNTAX INTEGER {
        default(1),
        unsupported(2147483647)
        }
    MAX-ACCESS read-write
    STATUS current
    DESCRIPTION
        "Setting the value to default(1) will set the Multiple
         Spanning Tree and member parameters to default.  default(1) is 
         always returned when read, but it does not mean anything.
         Note:This mib is not supported in vADC instance on Virtualization."
    ::= { mstCistCfg 1 }

-- CIST Brige Configuration
mstCistBridgeCfg  OBJECT IDENTIFIER ::= { mstCistCfg 2 }

mstCistCurCfgBridgePriority OBJECT-TYPE
    SYNTAX  INTEGER  (0..65535)
    MAX-ACCESS  read-only
    STATUS  current
    DESCRIPTION
        "The value of the writable portion of the Brigde Identifier comprising
         of the first two octets.
         Note:This mib is not supported in vADC instance on Virtualization."
    ::= { mstCistBridgeCfg 1 }

mstCistNewCfgBridgePriority OBJECT-TYPE
    SYNTAX  INTEGER  (0..65535)
    MAX-ACCESS  read-write
    STATUS  current
    DESCRIPTION
        "The value of the writable portion of the Brigde Identifier comprising
         of the first two octets.
         Note:This mib is not supported in vADC instance on Virtualization."
    ::= { mstCistBridgeCfg 2 }

mstCistCurCfgBridgeMaxAge OBJECT-TYPE
    SYNTAX  INTEGER  (6..40)
    MAX-ACCESS  read-only
    STATUS  current
    DESCRIPTION
        "The value in seconds that all bridges use for MaxAge when this bridge
         is acting as the root.
         Note:This mib is not supported in vADC instance on Virtualization."
    ::= { mstCistBridgeCfg 5 }

mstCistNewCfgBridgeMaxAge OBJECT-TYPE
    SYNTAX  INTEGER  (6..40)
    MAX-ACCESS  read-write
    STATUS  current
    DESCRIPTION
        "The value in seconds that all bridges use for MaxAge when this bridge
         is acting as the root.
         Note:This mib is not supported in vADC instance on Virtualization."
    ::= { mstCistBridgeCfg 6 }

mstCistCurCfgBridgeForwardDelay OBJECT-TYPE
    SYNTAX  INTEGER  (4..30)
    MAX-ACCESS  read-only
    STATUS  current
    DESCRIPTION
        "The value in seconds that all bridges use for ForwardDelay when this 
         bridge is acting as the root.
         Note:This mib is not supported in vADC instance on Virtualization."
    ::= { mstCistBridgeCfg 7 }

mstCistNewCfgBridgeForwardDelay OBJECT-TYPE
    SYNTAX  INTEGER  (4..30)
    MAX-ACCESS  read-write
    STATUS  current
    DESCRIPTION
        "The value in seconds that all bridges use for ForwardDelay when this 
         bridge is acting as the root.
         Note:This mib is not supported in vADC instance on Virtualization."
    ::= { mstCistBridgeCfg 8 }

-- CIST Port Configuration

mstCistCurCfgPortTable OBJECT-TYPE
    SYNTAX SEQUENCE OF MstCistCurCfgPortTableEntry
    MAX-ACCESS not-accessible
    STATUS current
    DESCRIPTION
        "The table of CIST Port configuration.
        Note:This mib is not supported in vADC instance on Virtualization."
    ::= { mstCistCfg 3 }

mstCistCurCfgPortTableEntry OBJECT-TYPE
    SYNTAX MstCistCurCfgPortTableEntry
    MAX-ACCESS not-accessible
    STATUS current
    DESCRIPTION
        "Information about a particular CIST Port configuration.
        Note:This mib is not supported in vADC instance on Virtualization."
    INDEX { mstCistCurCfgPortIndex }
    ::= { mstCistCurCfgPortTable 1 }

MstCistCurCfgPortTableEntry ::= SEQUENCE {
    mstCistCurCfgPortIndex      Integer32,
    mstCistCurCfgPortPriority   INTEGER,
    mstCistCurCfgPortPathCost   INTEGER,
    mstCistCurCfgPortLinkType   INTEGER,
    mstCistCurCfgPortEdge       INTEGER,
    mstCistCurCfgPortStpState   INTEGER,
    mstCistCurCfgPortHelloTime  INTEGER
    }

mstCistCurCfgPortIndex OBJECT-TYPE
    SYNTAX Integer32
    MAX-ACCESS read-only
    STATUS current
    DESCRIPTION
        "The port number of the port for which this entry contains spanning
         tree configuration.
         Note:This mib is not supported in vADC instance on Virtualization."
    ::= { mstCistCurCfgPortTableEntry 1 }

mstCistCurCfgPortPriority OBJECT-TYPE
    SYNTAX INTEGER (0..240)
    MAX-ACCESS read-only
    STATUS current
    DESCRIPTION
        "The four most significant bits of the Port Identifier of the 
         Spanning Tree instance can be modified by setting this value.
         Note:This mib is not supported in vADC instance on Virtualization."
    ::= { mstCistCurCfgPortTableEntry 2 }

mstCistCurCfgPortPathCost OBJECT-TYPE
    SYNTAX INTEGER (1..200000000)
    MAX-ACCESS read-only
    STATUS current
    DESCRIPTION
        "The contribution of this port to the path cost of paths towards 
         the CIST Root which include this port.
         Note:This mib is not supported in vADC instance on Virtualization."
    ::= { mstCistCurCfgPortTableEntry 3 }

mstCistCurCfgPortLinkType OBJECT-TYPE
    SYNTAX INTEGER {
        auto(1),
        p2p(2),
        shared(3),
        unsupported(2147483647)
        }
    MAX-ACCESS read-only
    STATUS current
    DESCRIPTION
        "The administrative point-to-point status of the LAN segment attached 
         to this port.  A value of p2p (2) indicates that this port should 
         always be treated as if it is connected to a point-to-point link. 
         A value of shared(3) indicates that this port should be treated as 
         having a shared media connection.  A value of auto(1) indicates that 
         this port is considered to have a point-to-point link if it is an 
         Aggregator and all of its members are aggregatable, or if the MAC 
         entity is configured for full duplex operation, either through
         auto-negotiation or by management means.
         Note:This mib is not supported in vADC instance on Virtualization."    
    ::= { mstCistCurCfgPortTableEntry 4 }

mstCistCurCfgPortEdge OBJECT-TYPE
    SYNTAX INTEGER {
        enabled(1),
        disabled(2),
        unsupported(2147483647)
        }
    MAX-ACCESS read-only
    STATUS current
    DESCRIPTION
        "The value of the Edge Port parameter.
        Note:This mib is not supported in vADC instance on Virtualization."
    ::= { mstCistCurCfgPortTableEntry 5 }

mstCistCurCfgPortStpState OBJECT-TYPE
    SYNTAX INTEGER {
        on(1),
        off(2),
        unsupported(2147483647)
        }
    MAX-ACCESS read-only
    STATUS current
    DESCRIPTION
        "Turn port's Spanning Tree on/off.
        Note:This mib is not supported in vADC instance on Virtualization."
    ::= { mstCistCurCfgPortTableEntry 6 }

mstCistCurCfgPortHelloTime OBJECT-TYPE
    SYNTAX  INTEGER (1..10)
    MAX-ACCESS  read-only
    STATUS  current
    DESCRIPTION
        "The amount of time between the transmission of Configuration Port 
         PDUs in seconds.
         Note:This mib is not supported in vADC instance on Virtualization."
    ::= { mstCistCurCfgPortTableEntry 7 } 

mstCistNewCfgPortTable OBJECT-TYPE
    SYNTAX SEQUENCE OF MstCistNewCfgPortTableEntry
    MAX-ACCESS not-accessible
    STATUS current
    DESCRIPTION
        "The table of CIST Port configuration.
        Note:This mib is not supported in vADC instance on Virtualization."
    ::= { mstCistCfg 4 }

mstCistNewCfgPortTableEntry OBJECT-TYPE
    SYNTAX MstCistNewCfgPortTableEntry
    MAX-ACCESS not-accessible
    STATUS current
    DESCRIPTION
        "Information about a particular CIST Port configuration.
        Note:This mib is not supported in vADC instance on Virtualization."
    INDEX { mstCistNewCfgPortIndex }
    ::= { mstCistNewCfgPortTable 1 }

MstCistNewCfgPortTableEntry ::= SEQUENCE {
    mstCistNewCfgPortIndex      Integer32,
    mstCistNewCfgPortPriority   INTEGER,
    mstCistNewCfgPortPathCost   INTEGER,
    mstCistNewCfgPortLinkType   INTEGER,
    mstCistNewCfgPortEdge       INTEGER,
    mstCistNewCfgPortStpState   INTEGER,
    mstCistNewCfgPortHelloTime  INTEGER
    }

mstCistNewCfgPortIndex OBJECT-TYPE
    SYNTAX Integer32
    MAX-ACCESS read-only
    STATUS current
    DESCRIPTION
        "The port number of the port for which this entry contains spanning
         tree configuration.
         Note:This mib is not supported in vADC instance on Virtualization."
    ::= { mstCistNewCfgPortTableEntry 1 }

mstCistNewCfgPortPriority OBJECT-TYPE
    SYNTAX INTEGER (0..240)
    MAX-ACCESS read-write
    STATUS current
    DESCRIPTION
        "The four most significant bits of the Port Identifier of the 
         Spanning Tree instance can be modified by setting this value.
         Note:This mib is not supported in vADC instance on Virtualization."
    ::= { mstCistNewCfgPortTableEntry 2 }

mstCistNewCfgPortPathCost OBJECT-TYPE
    SYNTAX INTEGER (0..200000000)
    MAX-ACCESS read-write
    STATUS current
    DESCRIPTION
        "The contribution of this port to the path cost of paths towards 
         the CIST Root which include this port.
         Note:This mib is not supported in vADC instance on Virtualization."
    ::= { mstCistNewCfgPortTableEntry 3 }

mstCistNewCfgPortLinkType OBJECT-TYPE
    SYNTAX INTEGER {
        auto(1),
        p2p(2),
        shared(3),
        unsupported(2147483647)
        }
    MAX-ACCESS read-write
    STATUS current
    DESCRIPTION
        "The administrative point-to-point status of the LAN segment attached 
         to this port.  A value of p2p (2) indicates that this port should 
         always be treated as if it is connected to a point-to-point link. 
         A value of shared(3) indicates that this port should be treated as 
         having a shared media connection.  A value of auto(1) indicates that 
         this port is considered to have a point-to-point link if it is an 
         Aggregator and all of its members are aggregatable, or if the MAC 
         entity is configured for full duplex operation, either through
         auto-negotiation or by management means.
         Note:This mib is not supported in vADC instance on Virtualization."    
    ::= { mstCistNewCfgPortTableEntry 4 }

mstCistNewCfgPortEdge OBJECT-TYPE
    SYNTAX INTEGER {
        enabled(1),
        disabled(2),
        unsupported(2147483647)
        }
    MAX-ACCESS read-write
    STATUS current
    DESCRIPTION
        "The value of the Edge Port parameter.
        Note:This mib is not supported in vADC instance on Virtualization."
    ::= { mstCistNewCfgPortTableEntry 5 }

mstCistNewCfgPortStpState OBJECT-TYPE
    SYNTAX INTEGER {
        on(1),
        off(2),
        unsupported(2147483647)
        }
    MAX-ACCESS read-write
    STATUS current
    DESCRIPTION
        "Turn port's Spanning Tree on/off.
        Note:This mib is not supported in vADC instance on Virtualization."
    ::= { mstCistNewCfgPortTableEntry 6 }

mstCistNewCfgPortHelloTime OBJECT-TYPE
    SYNTAX  INTEGER (1..10)
    MAX-ACCESS  read-write
    STATUS  current
    DESCRIPTION
        "The amount of time between the transmission of Configuration Port 
         PDUs in seconds.
         Note:This mib is not supported in vADC instance on Virtualization."
    ::= { mstCistNewCfgPortTableEntry 7 } 

-- Port Team

portTeamTableMaxSize OBJECT-TYPE
    SYNTAX  Integer32
    MAX-ACCESS  read-only
    STATUS  current
    DESCRIPTION
        "The maximum number of port teams."
    ::= { portTeamCfg 1 }

portTeamCurCfgTable OBJECT-TYPE
    SYNTAX  SEQUENCE OF PortTeamCurCfgTableEntry
    MAX-ACCESS  not-accessible
    STATUS  current
    DESCRIPTION
        "The port team current configuration."
    ::= { portTeamCfg 2 }

portTeamCurCfgTableEntry OBJECT-TYPE
    SYNTAX  PortTeamCurCfgTableEntry
    MAX-ACCESS  not-accessible
    STATUS  current
    DESCRIPTION
        "A row in the port team configuration table."
    INDEX   { portTeamCurCfgIndex }
    ::= { portTeamCurCfgTable 1 }

PortTeamCurCfgTableEntry ::= SEQUENCE {
    portTeamCurCfgIndex         Integer32,
    portTeamCurCfgState         INTEGER,
    portTeamCurCfgPorts         OCTET STRING,
    portTeamCurCfgTrunks        OCTET STRING,
    portTeamCurCfgName          DisplayString
    }

portTeamCurCfgIndex OBJECT-TYPE
    SYNTAX  Integer32
    MAX-ACCESS  read-only
    STATUS  current
    DESCRIPTION
        "The identifier of the port team."
    ::= { portTeamCurCfgTableEntry 1 }

portTeamCurCfgState OBJECT-TYPE
    SYNTAX  INTEGER  {
        enable(1),
        disable(2),
        unsupported(2147483647)
        }
    MAX-ACCESS  read-only
    STATUS  current
    DESCRIPTION
        "Enable or disable a port team."
    ::= { portTeamCurCfgTableEntry 2 }

portTeamCurCfgPorts OBJECT-TYPE
    SYNTAX  OCTET STRING
    MAX-ACCESS  read-only
    STATUS  current
    DESCRIPTION
        "The port list in the port team. The ports are presented in
         bitmap format.

         in receiving order:

             OCTET 1  OCTET 2  .....
             xxxxxxxx xxxxxxxx .....
             |    |||_ port 8
             |    ||
             |    ||___ port 7
             |    |____ port 6
             |      .    .   .
             |_________ port 1

         where x : 1 - The represented port belongs to the port team
                   0 - The represented port does not belong to the port team"
    ::= { portTeamCurCfgTableEntry 3 }

portTeamCurCfgTrunks OBJECT-TYPE
    SYNTAX  OCTET STRING
    MAX-ACCESS  read-only
    STATUS  current
    DESCRIPTION
        "The trunk list in the port team. The trunks are presented in
         bitmap format.

         in receiving order:

             OCTET 1  OCTET 2  .....
             xxxxxxxx xxxxxxxx .....
             |    |||_ trunk 8
             |    ||
             |    ||___ trunk 7
             |    |____ trunk 6
             |      .    .   .
             |_________ trunk 1

         where x : 1 - The represented trunk belongs to the port team
                   0 - The represented trunk does not belong to the port team"
    ::= { portTeamCurCfgTableEntry 4 }

portTeamCurCfgName OBJECT-TYPE
    SYNTAX DisplayString (SIZE(0..31))
    MAX-ACCESS read-only
    STATUS current
    DESCRIPTION
        "Name of the Port Team."
    ::= { portTeamCurCfgTableEntry 5 }

portTeamNewCfgTable OBJECT-TYPE
    SYNTAX  SEQUENCE OF PortTeamNewCfgTableEntry
    MAX-ACCESS  not-accessible
    STATUS  current
    DESCRIPTION
        "The port team new configuration."
    ::= { portTeamCfg 3 }

portTeamNewCfgTableEntry OBJECT-TYPE
    SYNTAX  PortTeamNewCfgTableEntry
    MAX-ACCESS  not-accessible
    STATUS  current
    DESCRIPTION
        "A row in the port team configuration table."
    INDEX   { portTeamNewCfgIndex }
    ::= { portTeamNewCfgTable 1 }

PortTeamNewCfgTableEntry ::= SEQUENCE {
    portTeamNewCfgIndex         Integer32,
    portTeamNewCfgState         INTEGER,
    portTeamNewCfgPorts         OCTET STRING,
    portTeamNewCfgAddPort       Integer32,
    portTeamNewCfgRemovePort    Integer32,
    portTeamNewCfgTrunks        OCTET STRING,
    portTeamNewCfgAddTrunk      Integer32,
    portTeamNewCfgRemoveTrunk   Integer32,
    portTeamNewCfgDelete        INTEGER,
    portTeamNewCfgName          DisplayString
    }

portTeamNewCfgIndex OBJECT-TYPE
    SYNTAX  Integer32
    MAX-ACCESS  read-only
    STATUS  current
    DESCRIPTION
        "The identifier of the port team."
    ::= { portTeamNewCfgTableEntry 1 }

portTeamNewCfgState OBJECT-TYPE
    SYNTAX  INTEGER  {
        enable(1),
        disable(2),
        unsupported(2147483647)
        }
    MAX-ACCESS  read-create 
    STATUS  current
    DESCRIPTION
        "Enable or disable a port team."
    ::= { portTeamNewCfgTableEntry 2 }

portTeamNewCfgPorts OBJECT-TYPE
    SYNTAX  OCTET STRING
    MAX-ACCESS  read-only
    STATUS  current
    DESCRIPTION
        "The port list in the port team. The ports are presented in
         bitmap format.

         in receiving order:

             OCTET 1  OCTET 2  .....
             xxxxxxxx xxxxxxxx .....
             |    |||_ port 8
             |    ||
             |    ||___ port 7
             |    |____ port 6
             |      .    .   .
             |_________ port 1

         where x : 1 - The represented port belongs to the port team
                   0 - The represented port does not belong to the port team"
    ::= { portTeamNewCfgTableEntry 3 }

portTeamNewCfgAddPort OBJECT-TYPE
    SYNTAX  Integer32
    MAX-ACCESS  read-create
    STATUS  current
    DESCRIPTION
        "The port to be added in the port team. When read, 0 is returned."
    ::= { portTeamNewCfgTableEntry 4 }

portTeamNewCfgRemovePort OBJECT-TYPE
    SYNTAX  Integer32
    MAX-ACCESS  read-create
    STATUS  current
    DESCRIPTION
        "The port to be deleted from the port team. When read, 0 is returned."
    ::= { portTeamNewCfgTableEntry 5 }

portTeamNewCfgTrunks OBJECT-TYPE
    SYNTAX  OCTET STRING
    MAX-ACCESS  read-only
    STATUS  current
    DESCRIPTION
        "The trunk list in the port team. The trunks are presented in
         bitmap format.

         in receiving order:

             OCTET 1  OCTET 2  .....
             xxxxxxxx xxxxxxxx .....
             |    |||_ trunk 8
             |    ||
             |    ||___ trunk 7
             |    |____ trunk 6
             |      .    .   .
             |_________ trunk 1

         where x : 1 - The represented trunk belongs to the port team
                   0 - The represented trunk does not belong to the port team"
    ::= { portTeamNewCfgTableEntry 6 }

portTeamNewCfgAddTrunk OBJECT-TYPE
    SYNTAX  Integer32
    MAX-ACCESS  read-create
    STATUS  current
    DESCRIPTION
        "The trunk to be added in the port team. When read, 0 is returned."
    ::= { portTeamNewCfgTableEntry 7 }

portTeamNewCfgRemoveTrunk OBJECT-TYPE
    SYNTAX  Integer32
    MAX-ACCESS  read-create
    STATUS  current
    DESCRIPTION
        "The trunk to be deleted from the port team. When read, 0 is returned."
    ::= { portTeamNewCfgTableEntry 8 }

portTeamNewCfgDelete OBJECT-TYPE
    SYNTAX  INTEGER  {
        other(1),
        delete(2),
        unsupported(2147483647)
        }
    MAX-ACCESS  read-create
    STATUS  current
    DESCRIPTION
        "Setting the value to delete(2) will delete the entire
         row. When read, other(1) is returned."
    ::= { portTeamNewCfgTableEntry 9 }

portTeamNewCfgName OBJECT-TYPE
    SYNTAX DisplayString (SIZE(0..31))
    MAX-ACCESS read-create
    STATUS current
    DESCRIPTION
        "Name of the Port Team."
    ::= { portTeamNewCfgTableEntry 10 }


hwBypassGeneralCfg  OBJECT IDENTIFIER ::= { hwBypassConfig 1 }

hwBypassCurState OBJECT-TYPE
    SYNTAX  INTEGER {
            enabled(2),
            disabled(3),
            unsupported(2147483647)
    }
    MAX-ACCESS  read-only
    STATUS  current
    DESCRIPTION
        "Hardware bypass current state."
    ::= { hwBypassGeneralCfg 1 }

hwBypassNewState OBJECT-TYPE
    SYNTAX  INTEGER {
            enabled(2),
            disabled(3),
            unsupported(2147483647)
    }
    MAX-ACCESS  read-write
    STATUS  current
    DESCRIPTION
        "Hardware bypass new state."
    ::= { hwBypassGeneralCfg 2 }
    

portTeamInfoTable OBJECT-TYPE
    SYNTAX  SEQUENCE OF PortTeamInfoTableEntry
    MAX-ACCESS  not-accessible
    STATUS  current
    DESCRIPTION
        "The port team information table."
    ::= { portTeamInfo 1 }
 
portTeamInfoTableEntry OBJECT-TYPE
    SYNTAX  PortTeamInfoTableEntry
    MAX-ACCESS  not-accessible
    STATUS  current
    DESCRIPTION
        "A row in the port team information table."
    INDEX   { portTeamInfoIndex }
    ::= { portTeamInfoTable 1 }
 
PortTeamInfoTableEntry ::= SEQUENCE {
    portTeamInfoIndex          Integer32,
    portTeamInfoState          INTEGER,
    portTeamInfoPorts          OCTET STRING,
    portTeamInfoPortsState     OCTET STRING,
    portTeamInfoTrunks         OCTET STRING,
    portTeamInfoTrunksState    OCTET STRING,
    portTeamInfoMaster         DisplayString
    }

portTeamInfoIndex OBJECT-TYPE
    SYNTAX  Integer32
    MAX-ACCESS  read-only
    STATUS  current
    DESCRIPTION
        "The identifier of the port team."
    ::= { portTeamInfoTableEntry 1 }
 
portTeamInfoState OBJECT-TYPE
    SYNTAX  INTEGER  {
        off(1),
        passive(2),
        active(3),
        unsupported(2147483647)
        }
    MAX-ACCESS  read-only
    STATUS  current
    DESCRIPTION
        "State of a port team."
    ::= { portTeamInfoTableEntry 2 }
 
portTeamInfoPorts OBJECT-TYPE
    SYNTAX  OCTET STRING
    MAX-ACCESS  read-only
    STATUS  current
    DESCRIPTION
        "The port list in the port team. The ports are presented in
         bitmap format.
 
         in receiving order:

             OCTET 1  OCTET 2  .....
             xxxxxxxx xxxxxxxx .....
             |    |||_ port 8
             |    ||
             |    ||___ port 7
             |    |____ port 6
             |      .    .   .
             |_________ port 1

         where x : 1 - The represented port is added to the port team
                   0 - The represented port is not added to the port team"
    ::= { portTeamInfoTableEntry 3 }
 
portTeamInfoPortsState OBJECT-TYPE
    SYNTAX  OCTET STRING
    MAX-ACCESS  read-only
    STATUS  current
    DESCRIPTION
        "The port state list in the port team. The ports states are presented in
         bitmap format.
 
         in receiving order:

             OCTET 1  OCTET 2  .....
             xxxxxxxx xxxxxxxx .....
             |    |||_ port 8 state
             |    ||
             |    ||___ port 7 state
             |    |____ port 6 state
             |      .    .   .
             |_________ port 1 state

         where x : 1 - The represented port in that team is up
                   0 - If the represented port is added in that team then
                       the port state is down otherwise the port is not 
                       added into that team( check whether port is added 
                       to the team or not through the mib portTeamInfoPorts)."
    ::= { portTeamInfoTableEntry 4 }
 
portTeamInfoTrunks OBJECT-TYPE
    SYNTAX  OCTET STRING
    MAX-ACCESS  read-only
    STATUS  current
    DESCRIPTION
        "The trunk list in the port team. The trunks are presented in
         bitmap format.
 
         in receiving order:

             OCTET 1  OCTET 2  .....
             xxxxxxxx xxxxxxxx .....
             |    |||_ trunk 8
             |    ||
             |    ||___ trunk 7
             |    |____ trunk 6
             |      .    .   .
             |_________ trunk 1

         where x : 1 - The represented trunk belongs to the port team
                   0 - The represented trunk does not belong to the port team"
    ::= { portTeamInfoTableEntry 5 }

portTeamInfoTrunksState OBJECT-TYPE
    SYNTAX  OCTET STRING
    MAX-ACCESS  read-only
    STATUS  current
    DESCRIPTION
        "The trunk state list in the trunk team. The trunks states are presented in
         bitmap format.

         in receiving order:

             OCTET 1  OCTET 2  .....
             xxxxxxxx xxxxxxxx .....
             |    |||_ trunk 8 state
             |    ||
             |    ||___ trunk 7 state
             |    |____ trunk 6 state
             |      .    .   .
             |_________ trunk 1 state

         where x : 1 - The represented trunk in that team is up
                   0 - If the represented trunk is added in that team then
                       the trunk state is down otherwise the port is
                       not added into that team( check whether it is added
                       to the team or not through the mib portTeamInfoTrunks)."
    ::= { portTeamInfoTableEntry 6 }

portTeamInfoMaster OBJECT-TYPE
    SYNTAX  DisplayString
    MAX-ACCESS  read-only
    STATUS  current
    DESCRIPTION
        "The master port/trunk of the port team when team state is ACTIVE."
    ::= { portTeamInfoTableEntry 7 }


vadcVlanCurCfgTable OBJECT-TYPE
    SYNTAX  SEQUENCE OF VadcVlanCurCfgTableEntry
    MAX-ACCESS  not-accessible
    STATUS  current
    DESCRIPTION
        "The vADC table of VLAN configuration.
        Note:This mib is supported only in vADC instance of virtualization."
    ::= { vadcVlan 1 }

vadcVlanCurCfgTableEntry OBJECT-TYPE
    SYNTAX  VadcVlanCurCfgTableEntry
    MAX-ACCESS  not-accessible
    STATUS  current
    DESCRIPTION
        "A row in the VLAN configuration table.
        Note:This mib is supported only in vADC instance of virtualization."
    INDEX  { vadcVlanCurCfgVlanId }
    ::= { vadcVlanCurCfgTable 1 }

VadcVlanCurCfgTableEntry ::= SEQUENCE {
    vadcVlanCurCfgVlanId        Integer32,
    vadcVlanCurCfgBwmCont       Integer32,
    vadcVlanCurCfgNonIp         Integer32,
    vadcVlanCurCfgIpv6LlaGen    INTEGER,
    vadcVlanCurCfgRouterAdv     INTEGER,
    vadcVlanCurCfgReTransInt    Unsigned32,
    vadcVlanCurCfgMinIntBwAdv   INTEGER,
    vadcVlanCurCfgMaxIntBwAdv   INTEGER,
    vadcVlanCurCfgMtu           INTEGER,
    vadcVlanCurCfgCurHopLimit   INTEGER,
    vadcVlanCurCfgMFlag         INTEGER,
    vadcVlanCurCfgOFlag         INTEGER,
    vadcVlanCurCfgRTime         INTEGER,
    vadcVlanCurCfgRlTime        INTEGER,
    vadcVlanCurCfgPlTime        Unsigned32,
    vadcVlanCurCfgVlTime        Unsigned32,
    vadcVlanCurCfgOpInfo        INTEGER,
    vadcVlanCurCfgApInfo        INTEGER,
    vadcVlanCurCfgIpv6Lla       DisplayString
    }

vadcVlanCurCfgVlanId OBJECT-TYPE
    SYNTAX  Integer32
    MAX-ACCESS  read-only
    STATUS  current
    DESCRIPTION
        "The VLAN identifier.
        Note:This mib is supported only in vADC instance of virtualization."
    ::= { vadcVlanCurCfgTableEntry 1 }

vadcVlanCurCfgBwmCont OBJECT-TYPE
    SYNTAX  Integer32
    MAX-ACCESS  read-only
    STATUS  current
    DESCRIPTION
        "Default contract number for the VLAN
        Note:This mib is supported only in vADC instance of virtualization."
    ::= { vadcVlanCurCfgTableEntry 2 }

vadcVlanCurCfgNonIp OBJECT-TYPE
    SYNTAX  Integer32
    MAX-ACCESS  read-only
    STATUS  current
    DESCRIPTION
        "BWM contract for non-ip traffic
        Note:This mib is supported only in vADC instance of virtualization."
        ::= { vadcVlanCurCfgTableEntry 3 }

vadcVlanCurCfgIpv6LlaGen OBJECT-TYPE
    SYNTAX INTEGER {
        enabled(2),
            disabled(3),
        unsupported(2147483647)
    }
    MAX-ACCESS read-only
    STATUS current
    DESCRIPTION
        "Enable/disable IPv6 Link Local Address Generation.
        Note:This mib is supported only in vADC instance of virtualization."
    ::= { vadcVlanCurCfgTableEntry 4 }

vadcVlanCurCfgRouterAdv OBJECT-TYPE
    SYNTAX INTEGER {
        enabled(2),
            disabled(3),
        unsupported(2147483647)
    }
    MAX-ACCESS read-only
    STATUS current
    DESCRIPTION
        "Enable/disable router advertisement.
        Note:This mib is supported only in vADC instance of virtualization."
    ::= { vadcVlanCurCfgTableEntry 5 }

vadcVlanCurCfgReTransInt OBJECT-TYPE
    SYNTAX Unsigned32 ( 0 .. 4294967295 )
    MAX-ACCESS read-only
    STATUS current
    DESCRIPTION
        "Retransmission interval.
        Note:This mib is supported only in vADC instance of virtualization."
    ::= { vadcVlanCurCfgTableEntry 6 }

vadcVlanCurCfgMinIntBwAdv OBJECT-TYPE
    SYNTAX INTEGER ( 3 .. 1800 )
    MAX-ACCESS read-only
    STATUS current
    DESCRIPTION
        "Minimum interval between router advertisements.
        Note:This mib is supported only in vADC instance of virtualization."
    ::= { vadcVlanCurCfgTableEntry 7 }

vadcVlanCurCfgMaxIntBwAdv OBJECT-TYPE
    SYNTAX INTEGER ( 4 .. 1800 )
    MAX-ACCESS read-only
    STATUS current
    DESCRIPTION
        "Maximum interval between router advertisements.
        Note:This mib is supported only in vADC instance of virtualization."
    ::= { vadcVlanCurCfgTableEntry 8 }

vadcVlanCurCfgMtu OBJECT-TYPE
    SYNTAX INTEGER ( 1200 .. 1500 )
    MAX-ACCESS read-only
    STATUS current
    DESCRIPTION
        "Maximum Transmission Unit. Enter 0 for None.
        Note:This mib is supported only in vADC instance of virtualization."
    ::= { vadcVlanCurCfgTableEntry 9 }

vadcVlanCurCfgCurHopLimit OBJECT-TYPE
    SYNTAX INTEGER ( 0 .. 255 )
    MAX-ACCESS read-only
    STATUS current
    DESCRIPTION
        "Current hop limit field.
        Note:This mib is supported only in vADC instance of virtualization."
    ::= { vadcVlanCurCfgTableEntry 10 }

vadcVlanCurCfgMFlag OBJECT-TYPE
    SYNTAX INTEGER {
        enabled(2),
        disabled(3),
        unsupported(2147483647)
    }
    MAX-ACCESS read-only
    STATUS current
    DESCRIPTION
        "Enable / Disable Managed address configuration flag.
        Note:This mib is supported only in vADC instance of virtualization."
    ::= { vadcVlanCurCfgTableEntry 11 }


vadcVlanCurCfgOFlag OBJECT-TYPE
    SYNTAX INTEGER {
        enabled(2),
        disabled(3),
        unsupported(2147483647)
    }
    MAX-ACCESS read-only
    STATUS current
    DESCRIPTION
        "Enable / Disable Other address configuration flag.
        Note:This mib is supported only in vADC instance of virtualization."
    ::= { vadcVlanCurCfgTableEntry 12 }

vadcVlanCurCfgRTime OBJECT-TYPE
    SYNTAX INTEGER ( 0 .. 3600000 )
    MAX-ACCESS read-only
    STATUS current
    DESCRIPTION
        "Reachable time.
        Note:This mib is supported only in vADC instance of virtualization."
    ::= { vadcVlanCurCfgTableEntry 13 }

vadcVlanCurCfgRlTime OBJECT-TYPE
    SYNTAX INTEGER ( 0 .. 9000 )
    MAX-ACCESS read-only
    STATUS current
    DESCRIPTION
        "Life Time.Enter 0 for None
        Note:This mib is supported only in vADC instance of virtualization."
    ::= { vadcVlanCurCfgTableEntry 14 }

vadcVlanCurCfgPlTime OBJECT-TYPE
    SYNTAX Unsigned32 ( 0 .. 4294967295 )
    MAX-ACCESS read-only
    STATUS current
    DESCRIPTION
        "Preferred life time.
        Note:This mib is supported only in vADC instance of virtualization."
    ::= { vadcVlanCurCfgTableEntry 15 }

vadcVlanCurCfgVlTime OBJECT-TYPE
    SYNTAX Unsigned32 ( 0 .. 4294967295 )
    MAX-ACCESS read-only
    STATUS current
    DESCRIPTION
        "Valid life time.
        Note:This mib is supported only in vADC instance of virtualization."
    ::= { vadcVlanCurCfgTableEntry 16 }

vadcVlanCurCfgOpInfo OBJECT-TYPE
    SYNTAX INTEGER {
        enabled(2),
        disabled(3),
        unsupported(2147483647)
    }
    MAX-ACCESS read-only
    STATUS current
    DESCRIPTION
        "Enable / Disable On-link flag in prefix.
        Note:This mib is supported only in vADC instance of virtualization."
    ::= { vadcVlanCurCfgTableEntry 17 }

vadcVlanCurCfgApInfo OBJECT-TYPE
    SYNTAX INTEGER {
        enabled(2),
        disabled(3),
        unsupported(2147483647)
    }
    MAX-ACCESS read-only
    STATUS current
    DESCRIPTION
        "Enable / Disable Autonomous address configuration flag in prefix.
        Note:This mib is supported only in vADC instance of virtualization."
    ::= { vadcVlanCurCfgTableEntry 18 }

vadcVlanCurCfgIpv6Lla OBJECT-TYPE
    SYNTAX DisplayString (SIZE(0..40))
    MAX-ACCESS  read-only
    STATUS  current
    DESCRIPTION
        "IPV6 Link Local Address.
        Note:This mib is supported only in vADC instance of virtualization."
    ::= { vadcVlanCurCfgTableEntry 19 }

vadcVlanNewCfgTable OBJECT-TYPE
    SYNTAX  SEQUENCE OF VadcVlanNewCfgTableEntry
    MAX-ACCESS  not-accessible
    STATUS  current
    DESCRIPTION
        "The vADC table of VLAN configuration.
        Note:This mib is supported only in vADC instance of virtualization."
    ::= { vadcVlan 2 }

vadcVlanNewCfgTableEntry OBJECT-TYPE
    SYNTAX  VadcVlanNewCfgTableEntry
    MAX-ACCESS  not-accessible
    STATUS  current
    DESCRIPTION
        "A row in the VLAN configuration table.
        Note:This mib is supported only in vADC instance of virtualization."
    INDEX  { vadcVlanNewCfgVlanId }
    ::= { vadcVlanNewCfgTable 1 }

VadcVlanNewCfgTableEntry ::= SEQUENCE {
    vadcVlanNewCfgVlanId        Integer32,
    vadcVlanNewCfgBwmCont       Integer32,
    vadcVlanNewCfgNonIp         Integer32,
    vadcVlanNewCfgIpv6LlaGen    INTEGER,
    vadcVlanNewCfgRouterAdv     INTEGER,
    vadcVlanNewCfgReTransInt    Unsigned32,
    vadcVlanNewCfgMinIntBwAdv   INTEGER,
    vadcVlanNewCfgMaxIntBwAdv   INTEGER,
    vadcVlanNewCfgMtu           INTEGER,
    vadcVlanNewCfgCurHopLimit   INTEGER,
    vadcVlanNewCfgMFlag         INTEGER,
    vadcVlanNewCfgOFlag         INTEGER,
    vadcVlanNewCfgRTime         INTEGER,
    vadcVlanNewCfgRlTime        INTEGER,
    vadcVlanNewCfgPlTime        Unsigned32,
    vadcVlanNewCfgVlTime        Unsigned32,
    vadcVlanNewCfgOpInfo        INTEGER,
    vadcVlanNewCfgApInfo        INTEGER,
    vadcVlanNewCfgIpv6Lla       DisplayString
    }

vadcVlanNewCfgVlanId OBJECT-TYPE
    SYNTAX  Integer32
    MAX-ACCESS  read-only
    STATUS  current
    DESCRIPTION
        "The VLAN identifier.
        Note:This mib is supported only in vADC instance of virtualization."
    ::= { vadcVlanNewCfgTableEntry 1 }

vadcVlanNewCfgBwmCont OBJECT-TYPE
    SYNTAX  Integer32
    MAX-ACCESS  read-create
    STATUS  current
    DESCRIPTION
        "Default contract number for the VLAN
        Note:This mib is supported only in vADC instance of virtualization."
    ::= { vadcVlanNewCfgTableEntry 2 }

vadcVlanNewCfgNonIp OBJECT-TYPE
    SYNTAX  Integer32
    MAX-ACCESS  read-create
    STATUS  current
    DESCRIPTION
        "BWM contract for non-ip traffic
        Note:This mib is supported only in vADC instance of virtualization."
    ::= { vadcVlanNewCfgTableEntry 3 }

vadcVlanNewCfgIpv6LlaGen OBJECT-TYPE
    SYNTAX INTEGER {
        enabled(2),
        disabled(3),
        unsupported(2147483647)
    }
    MAX-ACCESS read-create
    STATUS current
    DESCRIPTION
        "Enable/disable IPv6 Link Local Address Generation.
        Note:This mib is supported only in vADC instance of virtualization."
    ::= { vadcVlanNewCfgTableEntry 4 }

vadcVlanNewCfgRouterAdv OBJECT-TYPE
    SYNTAX INTEGER {
        enabled(2),
        disabled(3),
        unsupported(2147483647)
    }
    MAX-ACCESS read-create
    STATUS current
    DESCRIPTION
        "Enable/disable router advertisement.
        Note:This mib is supported only in vADC instance of virtualization."
    ::= { vadcVlanNewCfgTableEntry 5 }

vadcVlanNewCfgReTransInt OBJECT-TYPE
    SYNTAX Unsigned32 ( 0 .. 4294967295 )
    MAX-ACCESS read-create
    STATUS current
    DESCRIPTION
        "Retransmission interval.
        Note:This mib is supported only in vADC instance of virtualization."
    ::= { vadcVlanNewCfgTableEntry 6 }

vadcVlanNewCfgMinIntBwAdv OBJECT-TYPE
    SYNTAX INTEGER ( 3 .. 1800 )
    MAX-ACCESS read-create
    STATUS current
    DESCRIPTION
        "Minimum interval between router advertisements.
        Note:This mib is supported only in vADC instance of virtualization."
    ::= { vadcVlanNewCfgTableEntry 7 }

vadcVlanNewCfgMaxIntBwAdv OBJECT-TYPE
    SYNTAX INTEGER ( 4 .. 1800 )
    MAX-ACCESS read-create
    STATUS current
    DESCRIPTION
        "Maximum interval between router advertisements.
        Note:This mib is supported only in vADC instance of virtualization."
    ::= { vadcVlanNewCfgTableEntry 8 }

vadcVlanNewCfgMtu OBJECT-TYPE
    SYNTAX INTEGER ( 1200 .. 1500 )
    MAX-ACCESS read-create
    STATUS current
    DESCRIPTION
        "Maximum Transmission Unit. Enter 0 for None.
        Note:This mib is supported only in vADC instance of virtualization."
    ::= { vadcVlanNewCfgTableEntry 9 }

vadcVlanNewCfgCurHopLimit OBJECT-TYPE
    SYNTAX INTEGER ( 0 .. 255 )
    MAX-ACCESS read-create
    STATUS current
    DESCRIPTION
        "Current hop limit field.
        Note:This mib is supported only in vADC instance of virtualization."
    ::= { vadcVlanNewCfgTableEntry 10 }

vadcVlanNewCfgMFlag OBJECT-TYPE
    SYNTAX INTEGER {
        enabled(2),
        disabled(3),
        unsupported(2147483647)
    }
    MAX-ACCESS read-create
    STATUS current
    DESCRIPTION
        "Enable / Disable Managed address configuration flag.
        Note:This mib is supported only in vADC instance of virtualization."
    ::= { vadcVlanNewCfgTableEntry 11 }

vadcVlanNewCfgOFlag OBJECT-TYPE
    SYNTAX INTEGER {
        enabled(2),
        disabled(3),
        unsupported(2147483647)
    }
    MAX-ACCESS read-create
    STATUS current
    DESCRIPTION
        "Enable / Disable Other address configuration flag.
        Note:This mib is supported only in vADC instance of virtualization."
::= { vadcVlanNewCfgTableEntry 12 }

vadcVlanNewCfgRTime OBJECT-TYPE
    SYNTAX INTEGER ( 0 .. 3600000 )
    MAX-ACCESS read-create
    STATUS current
    DESCRIPTION
        "Reachable time.
        Note:This mib is supported only in vADC instance of virtualization."
    ::= { vadcVlanNewCfgTableEntry 13 }

vadcVlanNewCfgRlTime OBJECT-TYPE
    SYNTAX INTEGER ( 0 .. 9000 )
    MAX-ACCESS read-create
    STATUS current
    DESCRIPTION
        "Life Time.Enter 0 for None
        Note:This mib is supported only in vADC instance of virtualization."
    ::= { vadcVlanNewCfgTableEntry 14 }

vadcVlanNewCfgPlTime OBJECT-TYPE
    SYNTAX Unsigned32 ( 0 .. 4294967295 ) 
    MAX-ACCESS read-create
    STATUS current
    DESCRIPTION
        "Preferred life time.
        Note:This mib is supported only in vADC instance of virtualization."
    ::= { vadcVlanNewCfgTableEntry 15 }

vadcVlanNewCfgVlTime OBJECT-TYPE
    SYNTAX Unsigned32 ( 0 .. 4294967295 )
    MAX-ACCESS read-create
    STATUS current
    DESCRIPTION
        "Valid life time.
        Note:This mib is supported only in vADC instance of virtualization."
    ::= { vadcVlanNewCfgTableEntry 16 }

vadcVlanNewCfgOpInfo OBJECT-TYPE
    SYNTAX INTEGER {
        enabled(2),
        disabled(3),
        unsupported(2147483647)
    }
    MAX-ACCESS read-create
    STATUS current
    DESCRIPTION
        "Enable / Disable On-link flag in prefix.
        Note:This mib is supported only in vADC instance of virtualization."
    ::= { vadcVlanNewCfgTableEntry 17 }

vadcVlanNewCfgApInfo OBJECT-TYPE
    SYNTAX INTEGER {
        enabled(2),
        disabled(3),
        unsupported(2147483647)
    }
    MAX-ACCESS read-create
    STATUS current
    DESCRIPTION
        "Enable / Disable Autonomous address configuration flag in prefix.
        Note:This mib is supported only in vADC instance of virtualization."
    ::= { vadcVlanNewCfgTableEntry 18 }

vadcVlanNewCfgIpv6Lla OBJECT-TYPE
    SYNTAX DisplayString (SIZE(0..40))
    MAX-ACCESS  read-create
    STATUS  current
    DESCRIPTION
        "IPV6 Link Local Address.
        Note:This mib is supported only in vADC instance of virtualization."
    ::= { vadcVlanNewCfgTableEntry 19 }


-- Link Layer Discovery Protocol (LLDP) 

lldpCurTxState OBJECT-TYPE
    SYNTAX  INTEGER {
        enabled(1),
        disabled(2),
        unsupported(2147483647)
        }
    MAX-ACCESS  read-only
    STATUS  current
    DESCRIPTION
        "Enable or disable LLDP transmission.
        Note:This mib is not supported in vADC instance on Virtualization."
    ::= { lldp 1 }

lldpNewTxState OBJECT-TYPE
    SYNTAX  INTEGER {
        enabled(1),
        disabled(2),
        unsupported(2147483647)
        }
    MAX-ACCESS read-create
    STATUS  current
    DESCRIPTION
        "Enable or disable LLDP transmission.
        Note:This mib is not supported in vADC instance on Virtualization."
    ::= { lldp 2 }

lldpCurTxInterval OBJECT-TYPE
    SYNTAX      INTEGER (2..600)
    MAX-ACCESS  read-only
    STATUS      current
    DESCRIPTION
            "The interval at which LLDP frames are transmitted on
            behalf of this LLDP agent.

            The default value for lldpCurTxInterval object is
            30 seconds.
            Note:This mib is not supported in vADC instance on Virtualization."
    ::= { lldp 3 }

lldpNewTxInterval OBJECT-TYPE
    SYNTAX      INTEGER (2..600)
    MAX-ACCESS  read-write
    STATUS      current
    DESCRIPTION
            "The interval at which LLDP frames are transmitted on
            behalf of this LLDP agent.

            The default value for lldpCurTxInterval object is
            30 seconds.
            Note:This mib is not supported in vADC instance on Virtualization."
    ::= { lldp 4 }

lldpCurTxHold OBJECT-TYPE
    SYNTAX      INTEGER (2..20)
    MAX-ACCESS  read-only
    STATUS      current
    DESCRIPTION
            "TX hold multiplier. 
	    The time-to-live value expressed as a multiple of the
	    lldpCurTxInterval object.
        Note:This mib is not supported in vADC instance on Virtualization."
    ::= { lldp 5 }

lldpNewTxHold OBJECT-TYPE
    SYNTAX      INTEGER (2..20)
    MAX-ACCESS  read-write
    STATUS      current
    DESCRIPTION
            "TX hold multiplier.
            The time-to-live value expressed as a multiple of the
            lldpCurTxInterval object.
            Note:This mib is not supported in vADC instance on Virtualization."
    ::= { lldp 6 }

lldpCurVendtlv OBJECT-TYPE
    SYNTAX  INTEGER {
        enabled(1),
        disabled(2),
        unsupported(2147483647)
        }
    MAX-ACCESS  read-only
    STATUS  current
    DESCRIPTION
        "Enable or disable publishing vendor specific TLVs.
        Note:This mib is not supported in vADC instance on Virtualization."
    ::= { lldp 7 }

lldpNewVendtlv OBJECT-TYPE
    SYNTAX  INTEGER {
        enabled(1),
        disabled(2),
        unsupported(2147483647)
        }
    MAX-ACCESS read-create 
    STATUS  current
    DESCRIPTION
        "Enable or disable publishing vendor specific TLVs.
        Note:This mib is not supported in vADC instance on Virtualization."
    ::= { lldp 8 }

lldpCurSysNametlv OBJECT-TYPE
    SYNTAX  INTEGER {
        enabled(1),
        disabled(2),
        unsupported(2147483647)
        }
    MAX-ACCESS  read-only
    STATUS  current
    DESCRIPTION
        "Enable or disable publishing system name TLVs.
        Note:This mib is not supported in vADC instance on Virtualization."
    ::= { lldp 9 }

lldpNewSysNametlv OBJECT-TYPE
    SYNTAX  INTEGER {
        enabled(1),
        disabled(2),
        unsupported(2147483647)
        }
    MAX-ACCESS read-create
    STATUS  current
    DESCRIPTION
        "Enable or disable publishing system name TLVs.
        Note:This mib is not supported in vADC instance on Virtualization."
    ::= { lldp 10 }


-- FDB Statistics
 
fdbStatsCreates OBJECT-TYPE
    SYNTAX  Counter32
    MAX-ACCESS  read-only
    STATUS  current
    DESCRIPTION
        "Number of entries created in the Forwarding Database."
    ::= { fdbStats 1 }

fdbStatsDeletes OBJECT-TYPE
    SYNTAX  Counter32
    MAX-ACCESS  read-only
    STATUS  current
    DESCRIPTION
        "Number of entries deleted from the Forwarding Database."
    ::= { fdbStats 2 }

fdbStatsCurrent OBJECT-TYPE
    SYNTAX  Gauge32
    MAX-ACCESS  read-only
    STATUS  current
    DESCRIPTION
        "Current number of entries in the Forwarding Database."
    ::= { fdbStats 3 }

fdbStatsHiwat OBJECT-TYPE
    SYNTAX  Integer32
    MAX-ACCESS  read-only
    STATUS  current
    DESCRIPTION
        "Highest number of entries recorded at any given time in the 
         Forwarding Database."
    ::= { fdbStats 4 }

fdbStatsLookups OBJECT-TYPE
    SYNTAX  Counter32
    MAX-ACCESS  read-only
    STATUS  current
    DESCRIPTION
        "Number of entry lookups in the Forwarding Database."
    ::= { fdbStats 5 }

fdbStatsLookupFails OBJECT-TYPE
    SYNTAX  Counter32
    MAX-ACCESS  read-only
    STATUS  current
    DESCRIPTION
        "Number of unsuccessful searches made in the Forwarding Database."
    ::= { fdbStats 6 }

fdbStatsFinds OBJECT-TYPE
    SYNTAX  Counter32
    MAX-ACCESS  read-only
    STATUS  current
    DESCRIPTION
        "Number of searches in the Forwarding Database."
    ::= { fdbStats 7 }

fdbStatsFindFails OBJECT-TYPE
    SYNTAX  Counter32
    MAX-ACCESS  read-only
    STATUS  current
    DESCRIPTION
        "Number of search failures in the Forwarding Database."
    ::= { fdbStats 8 }

fdbStatsFindOrCreates OBJECT-TYPE
    SYNTAX  Counter32
    MAX-ACCESS  read-only
    STATUS  current
    DESCRIPTION
        "Number of entries found or created in the Forwarding Database."
    ::= { fdbStats 9 }

fdbStatsOverflows OBJECT-TYPE
    SYNTAX  Counter32
    MAX-ACCESS  read-only
    STATUS  current
    DESCRIPTION
        "Number of entries overflowing the Forwarding Database."
    ::= { fdbStats 10 }

-- STP Statistics

stgStatsPortTable OBJECT-TYPE
    SYNTAX SEQUENCE OF StgStatsPortTableEntry
    MAX-ACCESS not-accessible
    STATUS current
    DESCRIPTION
        "The table of Spanning Tree Group port statistics."
    ::= { stpStats 1 }

stgStatsPortTableEntry OBJECT-TYPE
    SYNTAX StgStatsPortTableEntry
    MAX-ACCESS not-accessible
    STATUS current
    DESCRIPTION
        "Statistics about port of a particular Spanning Tree Group."
    INDEX { stgStatsStpIndex, stgStatsPortIndex }
    ::= { stgStatsPortTable 1 }

StgStatsPortTableEntry ::= SEQUENCE {
    stgStatsStpIndex            Integer32,
    stgStatsPortIndex	        Integer32,
    stgStatsPortRcvCfgBpdus     Integer32,
    stgStatsPortRcvTcnBpdus     Integer32,
    stgStatsPortXmtCfgBpdus     Integer32,
    stgStatsPortXmtTcnBpdus     Integer32, 
    stgStatsPortRcvMrstBpdus    Integer32,
    stgStatsPortXmtMrstBpdus    Integer32
    }

stgStatsStpIndex OBJECT-TYPE
    SYNTAX Integer32  
    MAX-ACCESS read-only
    STATUS current
    DESCRIPTION
        "The identifier of a particular Spanning Tree Group."
    ::= { stgStatsPortTableEntry 1 }

stgStatsPortIndex OBJECT-TYPE
    SYNTAX Integer32
    MAX-ACCESS read-only
    STATUS current
    DESCRIPTION
        "The port identifier of a particular Spanning Tree Group."
    ::= { stgStatsPortTableEntry 2 }

stgStatsPortRcvCfgBpdus OBJECT-TYPE
    SYNTAX Integer32 
    MAX-ACCESS read-only
    STATUS current
    DESCRIPTION
        "Number of Configuration BPDUs received on this port."
    ::= { stgStatsPortTableEntry 3 }

stgStatsPortRcvTcnBpdus OBJECT-TYPE
    SYNTAX Integer32 
    MAX-ACCESS read-only
    STATUS current
    DESCRIPTION
        "Number of TCN BPDUs received on this port."
    ::= { stgStatsPortTableEntry 4 }

stgStatsPortXmtCfgBpdus OBJECT-TYPE
    SYNTAX Integer32 
    MAX-ACCESS read-only
    STATUS current
    DESCRIPTION
        "Number of Configuration BPDUs trasmitted from the port."
    ::= { stgStatsPortTableEntry 5 }

stgStatsPortXmtTcnBpdus OBJECT-TYPE
    SYNTAX Integer32 
    MAX-ACCESS read-only
    STATUS current
    DESCRIPTION
        "Number of TCN BPDUs trasmitted from the port."
    ::= { stgStatsPortTableEntry 6 }

stgStatsPortRcvMrstBpdus OBJECT-TYPE
    SYNTAX Integer32
    MAX-ACCESS read-only
    STATUS current
    DESCRIPTION
        "Number of MST/RST BPDUs received on this port."
    ::= { stgStatsPortTableEntry 7 }

stgStatsPortXmtMrstBpdus OBJECT-TYPE
    SYNTAX Integer32
    MAX-ACCESS read-only
    STATUS current
    DESCRIPTION
        "Number of MST/RST BPDUs trasmitted from the port."
    ::= { stgStatsPortTableEntry 8 }

fdbClear OBJECT-TYPE
    SYNTAX  INTEGER {
        ok(1),
        clear(2),
        unsupported(2147483647)
        }
    MAX-ACCESS  read-write
    STATUS  current 
    DESCRIPTION
        "Setting this value to clear(2) clears the entire master FDB."
    ::= { fdbInfo 1 }

--  FDB table
fdbTable OBJECT-TYPE
    SYNTAX  SEQUENCE OF FdbEntry
    MAX-ACCESS  not-accessible
    STATUS  current
    DESCRIPTION
        "The table of FDB entries."
    ::= { fdbInfo 2 }

fdbEntry OBJECT-TYPE
    SYNTAX  FdbEntry
    MAX-ACCESS  not-accessible
    STATUS  current
    DESCRIPTION
        "A row in the FDB table"
    INDEX   { fdbMacAddr }
    ::= { fdbTable 1 }

FdbEntry ::= SEQUENCE {
    fdbMacAddr            PhysAddress,
    fdbVlan       	  Integer32,
    fdbSrcPort            Integer32,
    fdbSrcTrunk           Integer32,
    fdbState              INTEGER,
    fdbRefSps             DisplayString,
    fdbLearnedPort        Integer32,
    fdbAge            	  DisplayString,
    fdbRefPorts           DisplayString
    }

fdbMacAddr OBJECT-TYPE
    SYNTAX  PhysAddress
    MAX-ACCESS  read-only
    STATUS  current
    DESCRIPTION
        "The MAC address for the FDB entry."
    ::= { fdbEntry 1 }

fdbVlan OBJECT-TYPE 
    SYNTAX  Integer32 
    MAX-ACCESS  read-only 
    STATUS  current 
    DESCRIPTION 
        "The VLAN ID for the FDB entry." 
    ::= { fdbEntry 2 }

fdbSrcPort OBJECT-TYPE  
    SYNTAX  Integer32 
    MAX-ACCESS  read-only  
    STATUS  current  
    DESCRIPTION  
       "Either the value '0', or the port number of the port on which a frame 
        having a source address equal to the value of the corresponding 
        instance has been seen.  A value of '0' indicates that the port 
        number has not been learned but that the bridge does have some
        forwarding/filtering information about this address."
    ::= { fdbEntry 3 }

fdbState OBJECT-TYPE  
    SYNTAX  INTEGER {
        unknown(1),
        ignore(2),
        forward(3),
        flood(4),
        ffd(5),
        trunk(6),
        vir(7),
        vsr(8),
        vpr(9),
        other(10),
        unsupported(2147483647)
        }
    MAX-ACCESS  read-only  
    STATUS  current  
    DESCRIPTION  
        "The state of the FDB entry. The meanings of the values are :
         unknown(1) : the MAC address has not yet been learned by the switch
                      but has only been seen as a destination address
         forward(3) : the MAC address has been learned by the switch
         flood(4)   : the MAC address is a multicast destination address 
         trunk(6)   : frames with this MAC address are forwarded to trunk
                      group
         vir(7)     : frames with this MAC address are forwarded for L3 
                      processing"
    ::= { fdbEntry 4 }

fdbAge OBJECT-TYPE   
    SYNTAX  DisplayString (SIZE(0..32))
    MAX-ACCESS  read-only   
    STATUS  current   
    DESCRIPTION   
        "The age of this FDB entry."   
    ::= { fdbEntry 8 }

fdbRefPorts OBJECT-TYPE   
    SYNTAX  DisplayString (SIZE(0..32))
    MAX-ACCESS  read-only   
    STATUS  current   
    DESCRIPTION   
        "The referenced ports associated with this FDB entry."   
    ::= { fdbEntry 9 }

fdbRefSps OBJECT-TYPE   
    SYNTAX  DisplayString (SIZE(0..32))
    MAX-ACCESS  read-only   
    STATUS  current   
    DESCRIPTION   
        "The referenced SPs associated with this FDB entry."   
    ::= { fdbEntry 5 }

fdbLearnedPort OBJECT-TYPE   
    SYNTAX  Integer32  
    MAX-ACCESS  read-only   
    STATUS  current   
    DESCRIPTION   
        "The learned port associated with this FDB entry."   
    ::= { fdbEntry 6 }

fdbSrcTrunk OBJECT-TYPE
    SYNTAX  Integer32
    MAX-ACCESS  read-only
    STATUS  current
    DESCRIPTION
       "Either the value '0', or the trunk number of the trunk on which a frame
        having a source address equal to the value of the corresponding
        instance has been seen.  A value of '0' indicates that the source
        address is not associated with a trunk."
    ::= { fdbEntry 7 }

-- STP information

stpInfoTable OBJECT-TYPE
    SYNTAX SEQUENCE OF StpInfoTableEntry
    MAX-ACCESS not-accessible
    STATUS current
    DESCRIPTION
        "The table of Spanning Tree Group information."
    ::= { stpInfo 1 }

stpInfoTableEntry OBJECT-TYPE
    SYNTAX StpInfoTableEntry
    MAX-ACCESS not-accessible
    STATUS current
    DESCRIPTION
        "Information about a particular Spanning Tree Group."
    INDEX { stpInfoIndex }
    ::= { stpInfoTable 1 }

StpInfoTableEntry ::= SEQUENCE {
    stpInfoIndex              Integer32,
    stpInfoTimeSinceTopChange TimeTicks,
    stpInfoTopChanges         Counter32,
    stpInfoDesignatedRoot     BridgeId,
    stpInfoRootCost           Integer32,
    stpInfoRootPort           Integer32,
    stpInfoMaxAge             Integer32,
    stpInfoHelloTime          Integer32,
    stpInfoForwardDelay       Integer32,
    stpInfoHoldTime           Integer32,
    stpInfoTimeSinceTopChangeStr DisplayString
    }

stpInfoIndex OBJECT-TYPE
    SYNTAX Integer32
    MAX-ACCESS read-only
    STATUS current
    DESCRIPTION
        "The identifier of a particular Spanning Tree Group."
    ::= { stpInfoTableEntry 1 }

stpInfoTimeSinceTopChange OBJECT-TYPE
    SYNTAX  TimeTicks
    MAX-ACCESS  read-only
    STATUS  current
    DESCRIPTION
        "The time (in hundredths of a second) since the last time a topology 
         change was detected by the bridge entity."
    ::= { stpInfoTableEntry 2 }

stpInfoTopChanges OBJECT-TYPE
    SYNTAX  Counter32
    MAX-ACCESS  read-only
    STATUS  current
    DESCRIPTION
        "The total number of topology changes detected by this bridge since 
         the management entity was last reset or initialized."
    ::= { stpInfoTableEntry 3 }

stpInfoDesignatedRoot OBJECT-TYPE
    SYNTAX  BridgeId
    MAX-ACCESS  read-only
    STATUS  current
    DESCRIPTION
        "The bridge identifier of the root of the spanning tree as determined 
         by the Spanning Tree Protocol as executed by this node.  This value 
         is used as the Root Identifier parameter in all Configuration Bridge 
         PDUs originated by this node."
    ::= { stpInfoTableEntry 4 }

stpInfoRootCost OBJECT-TYPE
    SYNTAX  Integer32
    MAX-ACCESS  read-only
    STATUS  current
    DESCRIPTION
        "The cost of the path to the root as seen from this bridge."
    ::= { stpInfoTableEntry 5 }

stpInfoRootPort OBJECT-TYPE
    SYNTAX  Integer32
    MAX-ACCESS  read-only
    STATUS  current
    DESCRIPTION
        "The port number of the port which offers the lowest cost path from 
         this bridge to the root bridge."
    ::= { stpInfoTableEntry 6 }

stpInfoMaxAge OBJECT-TYPE
    SYNTAX  Integer32
    MAX-ACCESS  read-only
    STATUS  current
    DESCRIPTION
        "The maximum age of Spanning Tree Protocol information learned from 
         the network on any port before it is discarded, in units of 
         hundredths of a second.  This is the actual value that this bridge is
         currently using."
    ::= { stpInfoTableEntry 7 }

stpInfoHelloTime OBJECT-TYPE
    SYNTAX  Integer32
    MAX-ACCESS  read-only
    STATUS  current
    DESCRIPTION
        "The amount of time between the transmission of Configuration bridge 
         PDUs by this node on any port when it is the root of the spanning 
         tree or trying to become so, in units of hundredths of a second.
         This is the actual value that this bridge is currently using."
    ::= { stpInfoTableEntry 8 }

stpInfoForwardDelay OBJECT-TYPE
     SYNTAX  Integer32
     MAX-ACCESS  read-only
     STATUS  current
     DESCRIPTION
         "This time value, measured in units of hundredths of a second, 
          controls how fast a port changes its spanning state when moving 
          towards the Forwarding state.  The value determines how long the port
          stays in each of the Listening and Learning states, which precede 
          the Forwarding state.  This value is also used, when a topology 
          change has been detected and is underway, to age all dynamic entries
          in the Forwarding Database."
    ::= { stpInfoTableEntry 9 }

stpInfoHoldTime OBJECT-TYPE
    SYNTAX  Integer32
    MAX-ACCESS  read-only
    STATUS  current
    DESCRIPTION
        "This time value determines the interval length during which no more 
         than two Configuration bridge PDUs shall be transmitted by this node,
         in units of hundredths of a second."
    ::= { stpInfoTableEntry 10 }

stpInfoTimeSinceTopChangeStr OBJECT-TYPE
    SYNTAX DisplayString (SIZE(0..64))
    MAX-ACCESS  read-only
    STATUS  current
    DESCRIPTION
        "The time in format: Days, Hours, Minutes, Seconds. since the last time a topology
         change was detected by the bridge entity."
    ::= { stpInfoTableEntry 11 }

stpInfoPortTable OBJECT-TYPE
    SYNTAX SEQUENCE OF StpInfoPortTableEntry
    MAX-ACCESS not-accessible
    STATUS current
    DESCRIPTION
        "The table of Spanning Tree Group port information."
    ::= { stpInfo 2 }

stpInfoPortTableEntry OBJECT-TYPE
    SYNTAX StpInfoPortTableEntry
    MAX-ACCESS not-accessible
    STATUS current
    DESCRIPTION
        "Information about port configuration for a particular Spanning Tree
         Group."
    INDEX { stpInfoPortStpIndex, stpInfoPortIndex }
    ::= { stpInfoPortTable 1 }

StpInfoPortTableEntry ::= SEQUENCE {
    stpInfoPortStpIndex           Integer32,
    stpInfoPortIndex              Integer32,
    stpInfoPortState              INTEGER,
    stpInfoPortDesignatedRoot     BridgeId,
    stpInfoPortDesignatedCost     Integer32,
    stpInfoPortDesignatedBridge   BridgeId,
    stpInfoPortDesignatedPort     OCTET STRING,
    stpInfoPortForwardTransitions Counter32,
    stpInfoPortRole               INTEGER,
    stpInfoPortLinkType           INTEGER,
    stpInfoPortEdge               INTEGER,
    stpInfoPortPathCost           Integer32
   }

stpInfoPortStpIndex OBJECT-TYPE
    SYNTAX Integer32
    MAX-ACCESS read-only
    STATUS current
    DESCRIPTION
        "The identifier of a particular Spanning Tree Group."
    ::= { stpInfoPortTableEntry 1 }

stpInfoPortIndex OBJECT-TYPE
    SYNTAX Integer32
    MAX-ACCESS read-only
    STATUS current
    DESCRIPTION
        "The port identifier of a particular Spanning Tree Group."
    ::= { stpInfoPortTableEntry 2 }

stpInfoPortState OBJECT-TYPE
    SYNTAX  INTEGER {
        disabled(1),
        blocking(2),
        listening(3),
        learning(4),
        forwarding(5),
        broken(6),
        discarding(7),
        unsupported(2147483647)
        }
    MAX-ACCESS  read-only
    STATUS  current
    DESCRIPTION
        "The port's current state as defined by application of the Spanning 
         Tree Protocol.  This state controls what action a port takes on
         reception of a frame.  If the bridge has detected a port that is 
         malfunctioning it will place that port into the broken(6) state.  
         For ports which are disabled, this object will have a value of 
         disabled(1)."
    ::= { stpInfoPortTableEntry 3 }

stpInfoPortDesignatedRoot OBJECT-TYPE
    SYNTAX  BridgeId
    MAX-ACCESS  read-only
    STATUS  current
    DESCRIPTION
        "The unique Bridge Identifier of the Bridge recorded as the Root in 
         the Configuration BPDUs transmitted by the Designated Bridge for the
         segment to which the port is attached."
    ::= { stpInfoPortTableEntry 4 }

stpInfoPortDesignatedCost OBJECT-TYPE
    SYNTAX  Integer32
    MAX-ACCESS  read-only
    STATUS  current
    DESCRIPTION
        "The path cost of the Designated Port of the segment connected to this
         port.  This value is compared to the Root Path Cost field in received
         bridge PDUs."
    ::= { stpInfoPortTableEntry 5 }

stpInfoPortDesignatedBridge OBJECT-TYPE
    SYNTAX  BridgeId
    MAX-ACCESS  read-only
    STATUS  current
    DESCRIPTION
        "The Bridge Identifier of the bridge which this port considers to be 
         the Designated Bridge for this port's segment."
    ::= { stpInfoPortTableEntry 6 }

stpInfoPortDesignatedPort OBJECT-TYPE
    SYNTAX  OCTET STRING (SIZE (2))
    MAX-ACCESS  read-only
    STATUS  current
    DESCRIPTION
        "The Port Identifier of the port on the Designated Bridge for this 
         port's segment."
    ::= { stpInfoPortTableEntry 7 }

stpInfoPortForwardTransitions OBJECT-TYPE
    SYNTAX  Counter32
    MAX-ACCESS  read-only
    STATUS  current
    DESCRIPTION
        "The number of times this port has transitioned from the Learning 
         state to the Forwarding state."
    ::= { stpInfoPortTableEntry 8 }

stpInfoPortPathCost OBJECT-TYPE
    SYNTAX  Integer32
    MAX-ACCESS  read-only
    STATUS  current
    DESCRIPTION
        "The path cost of the port."
    ::= { stpInfoPortTableEntry 9 }

stpInfoPortRole OBJECT-TYPE
    SYNTAX  INTEGER {
        disabled(1),
        alternate(2),
        backup(3),
        root(4),
        designated(5),
        master(6),
        unknown(7),
        unsupported(2147483647)
        }
    MAX-ACCESS  read-only
    STATUS  current
    DESCRIPTION
        "The port role. Returns unknown(7) when MSTP/RSTP is not enabled,
         otherwise returns appropriate port role."
    ::= { stpInfoPortTableEntry 10 }

stpInfoPortLinkType OBJECT-TYPE
    SYNTAX  INTEGER {
        p2p(1),
        shared(2),
        unknown(3),
        unsupported(2147483647)
        }
    MAX-ACCESS  read-only
    STATUS  current
    DESCRIPTION
        "The point-to-point status of the LAN segment attached
         to this port.  A value of p2p (1) indicates that this port is being
         treated as if it is connected to a point-to-point link.
         A value of shared(2) indicates that this port is being treated as
         having a shared media connection."
    ::= { stpInfoPortTableEntry 11 }

stpInfoPortEdge OBJECT-TYPE
    SYNTAX  INTEGER {
        enabled(1),
        disabled(2),
        unsupported(2147483647)
        }
    MAX-ACCESS  read-only
    STATUS  current
    DESCRIPTION
        "The port is an edge port or not. Returns disabled(2) when the port is
	 not an edge port and returns enabled(1) when it is an edge port."
    ::= { stpInfoPortTableEntry 12 }

-- LACP information 
lacpInfoPortTable OBJECT-TYPE
    SYNTAX SEQUENCE OF LacpInfoPortTableEntry
    MAX-ACCESS not-accessible
    STATUS current
    DESCRIPTION
        "The table of LACP port information."
    ::= { lacpInfo 1 }

lacpInfoPortTableEntry OBJECT-TYPE
    SYNTAX LacpInfoPortTableEntry
    MAX-ACCESS not-accessible
    STATUS current
    DESCRIPTION
        "Information about a LACP port."
    INDEX { lacpInfoPortIndex }
    ::= { lacpInfoPortTable 1 }

LacpInfoPortTableEntry ::= SEQUENCE {
    lacpInfoPortIndex           Integer32,
    lacpInfoPortSelected        INTEGER,
    lacpInfoPortNtt             INTEGER,
    lacpInfoPortReadyN          INTEGER,
    lacpInfoPortMoved           INTEGER
    }

lacpInfoPortIndex OBJECT-TYPE
    SYNTAX Integer32
    MAX-ACCESS read-only
    STATUS current
    DESCRIPTION
        "The port identifier."
    ::= { lacpInfoPortTableEntry 1 }

lacpInfoPortSelected OBJECT-TYPE
    SYNTAX  INTEGER {
        selected(1),
        unselected(2),
        standby(3),
        unsupported(2147483647)
        }
    MAX-ACCESS  read-only
    STATUS  current
    DESCRIPTION
        "Selected flag value indicates that the selection logic has selected
         an appropriate Aggregator. A value of unselected indicates that no 
         aggregator is currently selected. A value of standby indicates that
         although the selection logic has selected an appropriate Aggregator,
         aggregation restrictions currently precent the port from being 
         enabled as part of the aggregation, and so the port is being held
         in standby condition." 
    ::= { lacpInfoPortTableEntry 2 }

lacpInfoPortNtt OBJECT-TYPE
    SYNTAX  INTEGER {
        true(1),
        false(2),
        unsupported(2147483647)
        }
    MAX-ACCESS read-only
    STATUS  current
    DESCRIPTION
        "Need to transmit flag. True indicates that there is new protocol 
         information that should be transmitted on the link."
    ::= { lacpInfoPortTableEntry 3 }

lacpInfoPortReadyN OBJECT-TYPE
    SYNTAX  INTEGER {
        true(1),
        false(2),
        unsupported(2147483647)
        }
    MAX-ACCESS read-only
    STATUS  current
    DESCRIPTION
        "True value for Ready_N flag indicates that the wait while timer 
         has expired and it is waiting to attach to an aggregator. 
         There is one Ready_N value for each port."
    ::= { lacpInfoPortTableEntry 4 }

lacpInfoPortMoved OBJECT-TYPE
    SYNTAX  INTEGER {
        true(1),
        false(2),
        unsupported(2147483647)
        }
    MAX-ACCESS read-only
    STATUS  current
    DESCRIPTION
        "Port Moved flag is set to true if the receive machine for a port 
         is in the port_disabled state, and the combination of partner oper
         system and partner oper port number in use by the port has been 
         used by received in an incoming LACPDU on a different port."
    ::= { lacpInfoPortTableEntry 5 }

-- CIST Information

cistRoot OBJECT-TYPE
    SYNTAX  BridgeId
    MAX-ACCESS  read-only
    STATUS  current
    DESCRIPTION
        "The bridge identifier of the Root of the common spanning
         tree as determined by the Spanning Tree Protocol
         as executed by this node.  This value is used as
         the CIST Root Identifier parameter in all Configuration
         Bridge PDUs originated by this node."
    ::= { cistGeneralInfo 1 } 

cistRootPathCost OBJECT-TYPE
    SYNTAX  Integer32
    MAX-ACCESS  read-only
    STATUS  current
    DESCRIPTION
        "The cost of the path to the CIST Root as seen from this bridge."
    ::= { cistGeneralInfo 2 } 

cistRootPort OBJECT-TYPE
    SYNTAX  Integer32
    MAX-ACCESS  read-only
    STATUS  current
    DESCRIPTION 
        "The Port Number of the Port which offers the lowest path cost from 
        this bridge to the CIST Root Bridge."
    ::= { cistGeneralInfo 3 } 

cistBridgeHelloTime OBJECT-TYPE
    SYNTAX  Integer32
    MAX-ACCESS  read-only
    STATUS  current
    DESCRIPTION
        "The amount of time between the transmission of Configuration bridge
         PDUs in seconds."
    ::= { cistGeneralInfo 4 } 

cistBridgeMaxAge OBJECT-TYPE
    SYNTAX  Integer32
    MAX-ACCESS  read-only
    STATUS  current
    DESCRIPTION
        "The value in seconds that all bridges use for MaxAge when this bridge
         is acting as the root."
    ::= { cistGeneralInfo 5 } 

cistBridgeForwardDelay OBJECT-TYPE
    SYNTAX  Integer32
    MAX-ACCESS  read-only
    STATUS  current
    DESCRIPTION
        "The value in seconds that all bridges use for ForwardDelay when this 
         bridge is acting as the root."
    ::= { cistGeneralInfo 6 } 

cistRegionalRoot OBJECT-TYPE
    SYNTAX  BridgeId
    MAX-ACCESS  read-only
    STATUS  current
    DESCRIPTION
        "The bridge identifier of the Root of the Multiple
         spanning tree region as determined by the Spanning Tree
         Protocol as executed by this node.  This value is used as
         the CIST Regional Root Identifier parameter in all Configuration
         Bridge PDUs originated by this node."
   ::= { cistGeneralInfo 7 } 

cistRegionalPathCost OBJECT-TYPE
    SYNTAX  Integer32
    MAX-ACCESS  read-only
    STATUS  current
    DESCRIPTION
        "The Cost of the path to the CIST Regional Root as seen from this 
         bridge."
   ::= { cistGeneralInfo 8 } 


-- CIST Port Information Table
cistInfoPortTable OBJECT-TYPE
    SYNTAX SEQUENCE OF CistInfoPortTableEntry
    MAX-ACCESS not-accessible
    STATUS current
    DESCRIPTION
        "The table of CIST Port information."
    ::= { cistInfo 2 }

cistInfoPortTableEntry OBJECT-TYPE
    SYNTAX CistInfoPortTableEntry
    MAX-ACCESS not-accessible
    STATUS current
    DESCRIPTION
        "Information about a particular CIST Port."
    INDEX { cistInfoPortIndex }
    ::= { cistInfoPortTable 1 }

CistInfoPortTableEntry ::= SEQUENCE {
    cistInfoPortIndex            Integer32,
    cistInfoPortPriority         Integer32,
    cistInfoPortPathCost         Integer32,
    cistInfoPortState            INTEGER,
    cistInfoPortRole             INTEGER,
    cistInfoPortDesignatedBridge BridgeId,
    cistInfoPortDesignatedPort   OCTET STRING,
    cistInfoPortLinkType         INTEGER
    }

cistInfoPortIndex OBJECT-TYPE
    SYNTAX Integer32
    MAX-ACCESS read-only
    STATUS current
    DESCRIPTION
        "The port number of the port for which this entry contains spanning
         tree configuration."
    ::= { cistInfoPortTableEntry 1 }

cistInfoPortPriority OBJECT-TYPE
    SYNTAX Integer32
    MAX-ACCESS read-only
    STATUS current
    DESCRIPTION
        "The four most significant bits of the Port Identifier of the 
         Spanning Tree instance can be modified by setting this value."
    ::= { cistInfoPortTableEntry 2 }

cistInfoPortPathCost OBJECT-TYPE
    SYNTAX Integer32
    MAX-ACCESS read-only
    STATUS current
    DESCRIPTION
        "The contribution of this port to the path cost of paths towards 
         the CIST Root which include this port."
    ::= { cistInfoPortTableEntry 3 }

cistInfoPortState OBJECT-TYPE
    SYNTAX INTEGER {
        disabled (1),
        discarding (2),
        learning (4),
        forwarding (5),
        unsupported(2147483647)
        }
    MAX-ACCESS read-only
    STATUS current
    DESCRIPTION
        "Current state of the Port as defined by the Common    
         spanning tree protocol." 
    ::= { cistInfoPortTableEntry 4 }

cistInfoPortRole OBJECT-TYPE
    SYNTAX INTEGER {
        disabled(1),
        alternate(2),
        backup(3),
        root(4),
        designated(5),
        master(6),
        unknown(7),
        unsupported(2147483647)
        }
    MAX-ACCESS read-only
    STATUS current
    DESCRIPTION
          "Selected Port Role of the port for this spanning tree instance."
    ::= { cistInfoPortTableEntry 5 }

cistInfoPortDesignatedBridge OBJECT-TYPE
    SYNTAX  BridgeId
    MAX-ACCESS  read-only
    STATUS  current
    DESCRIPTION
        "The unique Bridge Identifier of the bridge which this port  
         considers to be the Designated Bridge for the port's segment."   
    ::= { cistInfoPortTableEntry 6 }

cistInfoPortDesignatedPort OBJECT-TYPE
    SYNTAX  OCTET STRING (SIZE (2))
    MAX-ACCESS  read-only
    STATUS  current
      DESCRIPTION
          "The Port identifier of the port on the Designated Bridge    
           for this port's segment."                                           
    ::= { cistInfoPortTableEntry 7 }

cistInfoPortLinkType OBJECT-TYPE
    SYNTAX INTEGER {
        p2p(1),
        shared(2),
        unknown(3),
        unsupported(2147483647)
        }
    MAX-ACCESS read-only
    STATUS current
    DESCRIPTION
        "The point-to-point status of the LAN segment attached 
         to this port.  A value of p2p (2) indicates that this port is being
         treated as if it is connected to a point-to-point link. 
         A value of shared(3) indicates that this port is being treated as 
         having a shared media connection."
    ::= { cistInfoPortTableEntry 8 }

-- VLAN information

vlanInfoTable OBJECT-TYPE
    SYNTAX SEQUENCE OF VlanInfoTableEntry
    MAX-ACCESS not-accessible
    STATUS current
    DESCRIPTION
        "The table of VLAN information."
    ::= { vlanInfo 1 }

vlanInfoTableEntry OBJECT-TYPE
    SYNTAX VlanInfoTableEntry
    MAX-ACCESS not-accessible
    STATUS current
    DESCRIPTION
        "Information about a particular VLAN."
    INDEX { vlanInfoId }
    ::= { vlanInfoTable 1 }

VlanInfoTableEntry ::= SEQUENCE {
    vlanInfoId                INTEGER,
    vlanInfoName 	      DisplayString,
    vlanInfoStatus            INTEGER,
    vlanInfoJumbo             INTEGER,
    vlanInfoBwmContract       Integer32,
    vlanInfoLearn             INTEGER,
    vlanInfoPorts             OCTET STRING,
    vlanInfoMTU               Integer32,
    vlanInfoFrag              INTEGER
    }

vlanInfoId OBJECT-TYPE
    SYNTAX  INTEGER  (1..4090)
    MAX-ACCESS read-only
    STATUS current
    DESCRIPTION
        "The VLAN identifier."
    ::= { vlanInfoTableEntry 1 }

vlanInfoName OBJECT-TYPE
    SYNTAX  DisplayString (SIZE(0..32))
    MAX-ACCESS  read-only
    STATUS  current
    DESCRIPTION
        "The VLAN name."
    ::= { vlanInfoTableEntry 2 }

vlanInfoStatus OBJECT-TYPE
    SYNTAX  INTEGER  {
	enabled(2),
	disabled(3),
        unsupported(2147483647)
	}
    MAX-ACCESS  read-only
    STATUS  current
    DESCRIPTION
        "Enable or disable, VLAN state information"
    ::= { vlanInfoTableEntry 3 }

vlanInfoJumbo OBJECT-TYPE
    SYNTAX  INTEGER  {
	enabled(2),
	disabled(3),
        unsupported(2147483647)
	}
    MAX-ACCESS  read-only
    STATUS  current
    DESCRIPTION
        "Enable or disable Jumbo frames, Jumbo frames state 
         information of a VLAN"
    ::= { vlanInfoTableEntry 4 }

vlanInfoBwmContract OBJECT-TYPE
    SYNTAX  Integer32
    MAX-ACCESS  read-only
    STATUS  current
    DESCRIPTION
        "Default BWM contract number information of a VLAN "
    ::= { vlanInfoTableEntry 5 }

vlanInfoLearn OBJECT-TYPE
    SYNTAX  INTEGER  {
        enabled(2),
        disabled(3),
        unsupported(2147483647)
        }
    MAX-ACCESS  read-only
    STATUS  current
    DESCRIPTION
        "Enable or disable source MAC address learning, MAC address
         learning information of a VLAN"
    ::= { vlanInfoTableEntry 6 }

vlanInfoPorts OBJECT-TYPE
    SYNTAX  OCTET STRING
    MAX-ACCESS  read-only
    STATUS  current
    DESCRIPTION
        "The port list information in the VLAN. The ports are presented 
         in bitmap format.
	 in receiving order:

	     OCTET 1  OCTET 2  .....
             xxxxxxxx xxxxxxxx ..... 
             ||    || |_ port 8
             ||    ||  
             ||    ||___ port 7
             ||    |____ port 6
             ||      .    .   .
             ||_________ port 1
             |__________ reserved

         where x : 1 - The represented port belongs to the VLAN
		   0 - The represented port does not belong to the VLAN"
    ::= { vlanInfoTableEntry 7 }

vlanInfoMTU OBJECT-TYPE
    SYNTAX  Integer32
    MAX-ACCESS  read-only
    STATUS  current
    DESCRIPTION
        "MTU informtation of a VLAN"
    ::= { vlanInfoTableEntry 8 }

vlanInfoFrag OBJECT-TYPE
    SYNTAX  INTEGER  {
        enabled(2),
        disabled(3),
        unsupported(2147483647)
        }
    MAX-ACCESS  read-only
    STATUS  current
    DESCRIPTION
        "Enable or disable, VLAN fragmentation state information"
    ::= { vlanInfoTableEntry 9 }

vlanInfoTableVADC OBJECT-TYPE
    SYNTAX SEQUENCE OF VlanInfoTableVADCEntry
    MAX-ACCESS not-accessible
    STATUS current
    DESCRIPTION
        "The table of VLAN information for vADC."
    ::= { vlanInfo 2 }

vlanInfoTableVADCEntry OBJECT-TYPE
    SYNTAX VlanInfoTableVADCEntry
    MAX-ACCESS not-accessible
    STATUS current
    DESCRIPTION
        "Information about a particular VLAN for vADC."
    INDEX { vlanInfoIdx }
    ::= { vlanInfoTableVADC 1 }

VlanInfoTableVADCEntry ::= SEQUENCE {
    vlanInfoIdx               INTEGER,
    vlanInfoVADC              DisplayString
    }

vlanInfoIdx OBJECT-TYPE
    SYNTAX  INTEGER  (1..4090)
    MAX-ACCESS read-only
    STATUS current
    DESCRIPTION
        "The VLAN identifier."
    ::= { vlanInfoTableVADCEntry 1 }

vlanInfoVADC OBJECT-TYPE
    SYNTAX DisplayString (SIZE(0..255)) 
    MAX-ACCESS read-only
    STATUS current
    DESCRIPTION
        "Display the VADC number which is connected to this VLAN."
    ::= { vlanInfoTableVADCEntry 2 } 


--- MTU and Jumbo Frames Configuration


mtuGeneralCfg  OBJECT IDENTIFIER ::= { mtuCfg 1 }

mtuCurValue OBJECT-TYPE
    SYNTAX  INTEGER  (1500..9216)
    MAX-ACCESS read-only
    STATUS current
    DESCRIPTION
        "The current config value of MTU"
    ::= { mtuGeneralCfg 1 }

mtuNewValue OBJECT-TYPE
    SYNTAX  INTEGER  (1500..9216)
    MAX-ACCESS read-write
    STATUS current
    DESCRIPTION
        "The new config value of MTU"
    ::= { mtuGeneralCfg 2 }

jumboSupported OBJECT-TYPE
    SYNTAX  INTEGER {
        yes(1),
        no(2)
        }
    MAX-ACCESS  read-only
    STATUS  current
    DESCRIPTION
        "State of whether the platform supports Jumbo Frames" 
    ::= { mtuGeneralCfg 3 }

END
